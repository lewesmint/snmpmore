-- PAN-TRAPS.my
--
-- MIB for the extended common MIB objects implemented by all
-- Palo Alto devices.
-- *********************************************** 

PAN-TRAPS DEFINITIONS ::= BEGIN

	 IMPORTS
		 MODULE-IDENTITY, OBJECT-IDENTITY,
		 OBJECT-TYPE, NOTIFICATION-TYPE,
		 Integer32, Counter64, Counter32
			 FROM SNMPv2-SMI
-- 		 MODULE-COMPLIANCE, OBJECT-GROUP
-- 			 FROM SNMPv2-CONF
		 DisplayString, TimeStamp, TruthValue
			 FROM SNMPv2-TC
		 TcChassisType
			 FROM PAN-GLOBAL-TC
		 panModules, panCommonMib
			 FROM PAN-GLOBAL-REG
		 panCommonEventObjs, panCommonEventEventsV2
			 FROM PAN-COMMON-MIB
		 InetAddressType, InetAddress
			 FROM INET-ADDRESS-MIB ;
    panTrapMibsModule MODULE-IDENTITY 
        LAST-UPDATED            "201805070000Z" 
        ORGANIZATION            "Palo Alto Networks" 
        CONTACT-INFO            " 
                    Customer Support 
                    Palo Alto Networks 
                    3000 Tannery Way 
                    Santa Clara, CA 95054 
 
                    +1 866-898-9087 
                    support at paloaltonetworks dot com" 
 
        DESCRIPTION             " 
            A MIB module containing definitions of managed objects 
            implemented by specific Palo Alto Networks products." 
 
        REVISION                "201805010000Z" 
        DESCRIPTION             " 
            Rev 9.0  
            Add Trap for IP-TAG logs." 
        REVISION                "201801010000Z" 
        DESCRIPTION             " 
            Rev 8.1  
            Add Trap for SCTP logs." 
        REVISION                "201711280000Z" 
        DESCRIPTION             "  
            Rev 8.0  
            Added Trap for GTP logs" 
        REVISION                "201710010000Z" 
        DESCRIPTION             " 
            Rev 7.0  
            Reorder attributes to match with the order defined in mib definition" 
        REVISION                "201606280000Z" 
        DESCRIPTION             "  
            Rev 6.0  
            Added Tunnel type support for vlan" 
        REVISION                "201601250000Z" 
        DESCRIPTION             " 
            Rev 5.0 
            Added panHttpMethod to threat trap" 
        REVISION                "201509300000Z" 
        DESCRIPTION             " 
            Rev 4.0 
            Added Traps to sync up with the latest System log events.
                  New BFD traps added. Addtional traps added for general,
                  GP, HA, HW, SSLMGR." 
        REVISION                "201502260000Z" 
        DESCRIPTION             " 
            Rev 3.0 
            Added Traps to sync up with the latest System log events.
                  Added InetAddressType and InetAddress types for 
                  IP address fields in order to support both IPV4 and IPV6
                  addresses and deprecated the IpAddress type." 
        REVISION                "201407090000Z" 
        DESCRIPTION             " 
            Rev 2.0 
            Added Traps to sync up with the latest System log events." 
        REVISION                "201106271040Z" 
        DESCRIPTION             " 
            Rev 1.0 
            Initial version of MIB module PAN-TRAPS." 
 
        ::= { panModules 5 } 
 
------------------------------------------------------------------------------
-- VARBINDS
------------------------------------------------------------------------------
--
--

	 panReceiveTime OBJECT-TYPE
		 SYNTAX 	 OCTET STRING (SIZE (1..32))
		 MAX-ACCESS 	 accessible-for-notify
		 STATUS 	 current
		 DESCRIPTION
		   "Time the log was received at the management plane."
		 ::= { panCommonEventObjs 2}
--
--

	 panSerial OBJECT-TYPE
		 SYNTAX 	 OCTET STRING (SIZE (1..16))
		 MAX-ACCESS 	 accessible-for-notify
		 STATUS 	 current
		 DESCRIPTION
		   "Serial number of the device that generated the log."
		 ::= { panCommonEventObjs 3}
--
--

	 panEventType OBJECT-TYPE
		 SYNTAX 	 OCTET STRING (SIZE (1..16))
		 MAX-ACCESS 	 accessible-for-notify
		 STATUS 	 current
		 DESCRIPTION
		   "Specifies type of log; Values are traffic, threat, config, system and hip-match."
		 ::= { panCommonEventObjs 4}
--
--

	 panEventSubType OBJECT-TYPE
		 SYNTAX 	 OCTET STRING (SIZE (1..16))
		 MAX-ACCESS 	 accessible-for-notify
		 STATUS 	 current
		 DESCRIPTION
		   "Subtype of traffic log; Values are start, end, drop, and deny."
		 ::= { panCommonEventObjs 5}
--
--

	 panHost OBJECT-TYPE
		 SYNTAX 	 IpAddress
		 MAX-ACCESS 	 accessible-for-notify
		 STATUS 	 current
		 DESCRIPTION
		   "Host address of PAN device that generated the event.This field is deprecated.
			Please use hostinetaddrtype and hostinetaddr."
		 ::= { panCommonEventObjs 6}
--
--

	 panVsys OBJECT-TYPE
		 SYNTAX 	 OCTET STRING (SIZE (0..32))
		 MAX-ACCESS 	 accessible-for-notify
		 STATUS 	 current
		 DESCRIPTION
		   "Virtual System associated with the session."
		 ::= { panCommonEventObjs 7}
--
--

	 panSeqno OBJECT-TYPE
		 SYNTAX 	 Counter64
		 MAX-ACCESS 	 accessible-for-notify
		 STATUS 	 current
		 DESCRIPTION
		   "A 64-bit log entry identifier incremented sequentially. Each log type has a unique number space"
		 ::= { panCommonEventObjs 8}
--
--

	 panActionflags OBJECT-TYPE
		 SYNTAX 	 OCTET STRING (SIZE (0..32))
		 MAX-ACCESS 	 accessible-for-notify
		 STATUS 	 current
		 DESCRIPTION
		   "A bit field indicating if the log was forwarded to Panorama."
		 ::= { panCommonEventObjs 9}
--
--

	 panHostInetAddrType OBJECT-TYPE
		 SYNTAX 	 InetAddressType
		 MAX-ACCESS 	 accessible-for-notify
		 STATUS 	 current
		 DESCRIPTION
		   "Host address type of PAN device that generated the event."
		 ::= { panCommonEventObjs 10}
--
--

	 panHostInetAddr OBJECT-TYPE
		 SYNTAX 	 InetAddress
		 MAX-ACCESS 	 accessible-for-notify
		 STATUS 	 current
		 DESCRIPTION
		   "Host address of PAN device that generated the event."
		 ::= { panCommonEventObjs 11}
--
--

	 panHostname OBJECT-TYPE
		 SYNTAX 	 OCTET STRING (SIZE (1..32))
		 MAX-ACCESS 	 accessible-for-notify
		 STATUS 	 current
		 DESCRIPTION
		   "Host name of the device that generated the trap."
		 ::= { panCommonEventObjs 12}
--
--

	 panSource OBJECT-TYPE
		 SYNTAX 	 OCTET STRING (SIZE (1..128))
		 MAX-ACCESS 	 accessible-for-notify
		 STATUS 	 current
		 DESCRIPTION
		   "Original session source IP address. This field is deprecated.
			Please use panSourceInetAddrType and panSourceInetAddr."
		 ::= { panCommonEventObjs 50}
--
--

	 panDestination OBJECT-TYPE
		 SYNTAX 	 OCTET STRING (SIZE (1..128))
		 MAX-ACCESS 	 accessible-for-notify
		 STATUS 	 current
		 DESCRIPTION
		   "Original session destination IP address. This field is deprecated.
			Please use panDestinationInetAddrType and panDestinationInetAddr."
		 ::= { panCommonEventObjs 51}
--
--

	 panNatSource OBJECT-TYPE
		 SYNTAX 	 OCTET STRING (SIZE (1..128))
		 MAX-ACCESS 	 accessible-for-notify
		 STATUS 	 current
		 DESCRIPTION
		   "If Source NAT performed, the post-NAT Source IP address. This field is deprecated.
			Please use panNatSourceInetAddrType and panNatSourceInetAddr."
		 ::= { panCommonEventObjs 52}
--
--

	 panNatDestination OBJECT-TYPE
		 SYNTAX 	 OCTET STRING (SIZE (1..128))
		 MAX-ACCESS 	 accessible-for-notify
		 STATUS 	 current
		 DESCRIPTION
		   "If Destination NAT performed, the post-NAT Destination IP address.
			This field is deprecated.Please use panNatDestinationInetAddrType and panNatDestinationInetAddr."
		 ::= { panCommonEventObjs 53}
--
--

	 panRule OBJECT-TYPE
		 SYNTAX 	 OCTET STRING (SIZE (1..64))
		 MAX-ACCESS 	 accessible-for-notify
		 STATUS 	 current
		 DESCRIPTION
		   "Name of the rule that the session matched."
		 ::= { panCommonEventObjs 54}
--
--

	 panSrcUser OBJECT-TYPE
		 SYNTAX 	 OCTET STRING (SIZE (1..64))
		 MAX-ACCESS 	 accessible-for-notify
		 STATUS 	 current
		 DESCRIPTION
		   "User name of the user that initiated the session."
		 ::= { panCommonEventObjs 55}
--
--

	 panDstUser OBJECT-TYPE
		 SYNTAX 	 OCTET STRING (SIZE (1..64))
		 MAX-ACCESS 	 accessible-for-notify
		 STATUS 	 current
		 DESCRIPTION
		   "User name of the user to which the session was destined."
		 ::= { panCommonEventObjs 56}
--
--

	 panApplication OBJECT-TYPE
		 SYNTAX 	 OCTET STRING (SIZE (1..32))
		 MAX-ACCESS 	 accessible-for-notify
		 STATUS 	 current
		 DESCRIPTION
		   "Application associated with the session."
		 ::= { panCommonEventObjs 57}
--
--

	 panSourceZone OBJECT-TYPE
		 SYNTAX 	 OCTET STRING (SIZE (1..16))
		 MAX-ACCESS 	 accessible-for-notify
		 STATUS 	 current
		 DESCRIPTION
		   "Zone the session was sourced from."
		 ::= { panCommonEventObjs 58}
--
--

	 panDestinationZone OBJECT-TYPE
		 SYNTAX 	 OCTET STRING (SIZE (1..16))
		 MAX-ACCESS 	 accessible-for-notify
		 STATUS 	 current
		 DESCRIPTION
		   "Zone the session was destined to."
		 ::= { panCommonEventObjs 59}
--
--

	 panIngressInterface OBJECT-TYPE
		 SYNTAX 	 OCTET STRING (SIZE (1..32))
		 MAX-ACCESS 	 accessible-for-notify
		 STATUS 	 current
		 DESCRIPTION
		   "Interface that the session was sourced form."
		 ::= { panCommonEventObjs 60}
--
--

	 panEgressInterface OBJECT-TYPE
		 SYNTAX 	 OCTET STRING (SIZE (1..32))
		 MAX-ACCESS 	 accessible-for-notify
		 STATUS 	 current
		 DESCRIPTION
		   "Interface that the session was destined to."
		 ::= { panCommonEventObjs 61}
--
--

	 panLogForwardingProfile OBJECT-TYPE
		 SYNTAX 	 OCTET STRING (SIZE (1..32))
		 MAX-ACCESS 	 accessible-for-notify
		 STATUS 	 current
		 DESCRIPTION
		   "Log Forwarding Profile that was applied to the session"
		 ::= { panCommonEventObjs 62}
--
--

	 panSessionID OBJECT-TYPE
		 SYNTAX 	 Counter32
		 MAX-ACCESS 	 accessible-for-notify
		 STATUS 	 current
		 DESCRIPTION
		   "An internal numerical identifier applied to each session."
		 ::= { panCommonEventObjs 63}
--
--

	 panRepeatCount OBJECT-TYPE
		 SYNTAX 	 Counter32
		 MAX-ACCESS 	 accessible-for-notify
		 STATUS 	 current
		 DESCRIPTION
		   "Number of sessions with same Source IP, Destination IP, Application, and Subtype seen within 5 seconds; Used for ICMP only."
		 ::= { panCommonEventObjs 64}
--
--

	 panSourcePort OBJECT-TYPE
		 SYNTAX 	 Counter32
		 MAX-ACCESS 	 accessible-for-notify
		 STATUS 	 current
		 DESCRIPTION
		   "Source port utilized by the session."
		 ::= { panCommonEventObjs 65}
--
--

	 panDestinationPort OBJECT-TYPE
		 SYNTAX 	 Counter32
		 MAX-ACCESS 	 accessible-for-notify
		 STATUS 	 current
		 DESCRIPTION
		   "Destination port utilized by the session."
		 ::= { panCommonEventObjs 66}
--
--

	 panNatSourcePort OBJECT-TYPE
		 SYNTAX 	 Counter32
		 MAX-ACCESS 	 accessible-for-notify
		 STATUS 	 current
		 DESCRIPTION
		   "Post-NAT source port."
		 ::= { panCommonEventObjs 67}
--
--

	 panNatDestinationPort OBJECT-TYPE
		 SYNTAX 	 Counter32
		 MAX-ACCESS 	 accessible-for-notify
		 STATUS 	 current
		 DESCRIPTION
		   "Post-NAT destination port."
		 ::= { panCommonEventObjs 68}
--
--

	 panFlags OBJECT-TYPE
		 SYNTAX 	 OCTET STRING (SIZE (1..16))
		 MAX-ACCESS 	 accessible-for-notify
		 STATUS 	 current
		 DESCRIPTION
		   "32 bit field that provides details on session."
		 ::= { panCommonEventObjs 69}
--
--

	 panProtocol OBJECT-TYPE
		 SYNTAX 	 OCTET STRING (SIZE (1..32))
		 MAX-ACCESS 	 accessible-for-notify
		 STATUS 	 current
		 DESCRIPTION
		   "IP protocol associated with the session"
		 ::= { panCommonEventObjs 70}
--
--

	 panAction OBJECT-TYPE
		 SYNTAX 	 OCTET STRING (SIZE (1..32))
		 MAX-ACCESS 	 accessible-for-notify
		 STATUS 	 current
		 DESCRIPTION
		   "Action taken for the session; Values are allow or deny"
		 ::= { panCommonEventObjs 71}
--
--

	 panTimeGenerated OBJECT-TYPE
		 SYNTAX 	 OCTET STRING (SIZE (1..32))
		 MAX-ACCESS 	 accessible-for-notify
		 STATUS 	 current
		 DESCRIPTION
		   "Time the log was generated on the data plane"
		 ::= { panCommonEventObjs 72}
--
--

	 panSrcloc OBJECT-TYPE
		 SYNTAX 	 OCTET STRING (SIZE (1..32))
		 MAX-ACCESS 	 accessible-for-notify
		 STATUS 	 current
		 DESCRIPTION
		   "Source country or Internal region for private addresses. Maximum length is 32 bytes."
		 ::= { panCommonEventObjs 73}
--
--

	 panDstloc OBJECT-TYPE
		 SYNTAX 	 OCTET STRING (SIZE (1..32))
		 MAX-ACCESS 	 accessible-for-notify
		 STATUS 	 current
		 DESCRIPTION
		   "Destination country or Internal region for private addresses. Maximum length is 32 bytes."
		 ::= { panCommonEventObjs 74}
--
--

	 panSourceInetAddrType OBJECT-TYPE
		 SYNTAX 	 InetAddressType
		 MAX-ACCESS 	 accessible-for-notify
		 STATUS 	 current
		 DESCRIPTION
		   "Original session source IP address type"
		 ::= { panCommonEventObjs 75}
--
--

	 panSourceInetAddr OBJECT-TYPE
		 SYNTAX 	 InetAddress
		 MAX-ACCESS 	 accessible-for-notify
		 STATUS 	 current
		 DESCRIPTION
		   "Original session source IP address."
		 ::= { panCommonEventObjs 76}
--
--

	 panDestinationInetAddrType OBJECT-TYPE
		 SYNTAX 	 InetAddressType
		 MAX-ACCESS 	 accessible-for-notify
		 STATUS 	 current
		 DESCRIPTION
		   "Original session destination IP address type."
		 ::= { panCommonEventObjs 77}
--
--

	 panDestinationInetAddr OBJECT-TYPE
		 SYNTAX 	 InetAddress
		 MAX-ACCESS 	 accessible-for-notify
		 STATUS 	 current
		 DESCRIPTION
		   "Original session destination IP address."
		 ::= { panCommonEventObjs 78}
--
--

	 panNatSourceInetAddrType OBJECT-TYPE
		 SYNTAX 	 InetAddressType
		 MAX-ACCESS 	 accessible-for-notify
		 STATUS 	 current
		 DESCRIPTION
		   "If Source NAT performed, the post-NAT Source IP address type"
		 ::= { panCommonEventObjs 79}
--
--

	 panNatSourceInetAddr OBJECT-TYPE
		 SYNTAX 	 InetAddress
		 MAX-ACCESS 	 accessible-for-notify
		 STATUS 	 current
		 DESCRIPTION
		   "If Source NAT performed, the post-NAT Source IP address."
		 ::= { panCommonEventObjs 80}
--
--

	 panNatDestinationInetAddrType OBJECT-TYPE
		 SYNTAX 	 InetAddressType
		 MAX-ACCESS 	 accessible-for-notify
		 STATUS 	 current
		 DESCRIPTION
		   "If Destination NAT performed, the post-NAT Destination IP address type"
		 ::= { panCommonEventObjs 81}
--
--

	 panNatDestinationInetAddr OBJECT-TYPE
		 SYNTAX 	 InetAddress
		 MAX-ACCESS 	 accessible-for-notify
		 STATUS 	 current
		 DESCRIPTION
		   "If Destination NAT performed, the post-NAT Destination IP address."
		 ::= { panCommonEventObjs 82}
--
--

	 panSourceUUID OBJECT-TYPE
		 SYNTAX 	 OCTET STRING (SIZE (1..36))
		 MAX-ACCESS 	 accessible-for-notify
		 STATUS 	 current
		 DESCRIPTION
		   "Source VM UUID for NSX. Maximum length is 36 bytes."
		 ::= { panCommonEventObjs 83}
--
--

	 panDestinationUUID OBJECT-TYPE
		 SYNTAX 	 OCTET STRING (SIZE (1..36))
		 MAX-ACCESS 	 accessible-for-notify
		 STATUS 	 current
		 DESCRIPTION
		   "Destination VM UUID for NSX. Maximum length is 36 bytes."
		 ::= { panCommonEventObjs 84}
--
--

	 panTunnel OBJECT-TYPE
		 SYNTAX 	 INTEGER { na (0), gre (1), ipsec (2), gtpu (3), gtp (4), vxlan (5) }
		 MAX-ACCESS 	 accessible-for-notify
		 STATUS 	 current
		 DESCRIPTION
		   "Types of Tunnel; Values are n/a, gre, ipsec, gtp, gtpu and vxlan."
		 ::= { panCommonEventObjs 85}
--
--

	 panRuleUUID OBJECT-TYPE
		 SYNTAX 	 OCTET STRING (SIZE (1..36))
		 MAX-ACCESS 	 accessible-for-notify
		 STATUS 	 current
		 DESCRIPTION
		   "Rule UUID for NSX. Maximum length is 36 bytes."
		 ::= { panCommonEventObjs 86}
--
--

	 panXffInetAddrType OBJECT-TYPE
		 SYNTAX 	 InetAddressType
		 MAX-ACCESS 	 accessible-for-notify
		 STATUS 	 current
		 DESCRIPTION
		   "Original session X-Forwarded-For IP address type"
		 ::= { panCommonEventObjs 87}
--
--

	 panXffInetAddr OBJECT-TYPE
		 SYNTAX 	 InetAddress
		 MAX-ACCESS 	 accessible-for-notify
		 STATUS 	 current
		 DESCRIPTION
		   "Original session X-Forwarded-For IP address."
		 ::= { panCommonEventObjs 88}
--
--

	 panContainerId OBJECT-TYPE
		 SYNTAX 	 OCTET STRING (SIZE (1..16))
		 MAX-ACCESS 	 accessible-for-notify
		 STATUS 	 current
		 DESCRIPTION
		   "Container ID"
		 ::= { panCommonEventObjs 89}
--
--

	 panPodNamespace OBJECT-TYPE
		 SYNTAX 	 OCTET STRING (SIZE (1..128))
		 MAX-ACCESS 	 accessible-for-notify
		 STATUS 	 current
		 DESCRIPTION
		   "POD Namespace"
		 ::= { panCommonEventObjs 90}
--
--

	 panPodName OBJECT-TYPE
		 SYNTAX 	 OCTET STRING (SIZE (1..128))
		 MAX-ACCESS 	 accessible-for-notify
		 STATUS 	 current
		 DESCRIPTION
		   "POD Name"
		 ::= { panCommonEventObjs 91}
--
--

	 panHostId OBJECT-TYPE
		 SYNTAX 	 OCTET STRING (SIZE (1..128))
		 MAX-ACCESS 	 accessible-for-notify
		 STATUS 	 current
		 DESCRIPTION
		   "Host ID"
		 ::= { panCommonEventObjs 92}
--
--

	 panSerialNo OBJECT-TYPE
		 SYNTAX 	 OCTET STRING (SIZE (1..128))
		 MAX-ACCESS 	 accessible-for-notify
		 STATUS 	 current
		 DESCRIPTION
		   "Serial Number"
		 ::= { panCommonEventObjs 93}
--
--

	 panTrafficBytes OBJECT-TYPE
		 SYNTAX 	 Counter64
		 MAX-ACCESS 	 accessible-for-notify
		 STATUS 	 current
		 DESCRIPTION
		   "Number of total bytes (transmit and receive) for the session."
		 ::= { panCommonEventObjs 100}
--
--

	 panTrafficPackets OBJECT-TYPE
		 SYNTAX 	 Counter32
		 MAX-ACCESS 	 accessible-for-notify
		 STATUS 	 current
		 DESCRIPTION
		   "Number of total packets (transmit and receive) for the session."
		 ::= { panCommonEventObjs 101}
--
--

	 panTrafficStartTime OBJECT-TYPE
		 SYNTAX 	 OCTET STRING (SIZE (1..32))
		 MAX-ACCESS 	 accessible-for-notify
		 STATUS 	 current
		 DESCRIPTION
		   "Time of session start."
		 ::= { panCommonEventObjs 102}
--
--

	 panTrafficElapsed OBJECT-TYPE
		 SYNTAX 	 TimeStamp
		 MAX-ACCESS 	 accessible-for-notify
		 STATUS 	 current
		 DESCRIPTION
		   "Elapsed time of the session."
		 ::= { panCommonEventObjs 103}
--
--

	 panTrafficCategory OBJECT-TYPE
		 SYNTAX 	 OCTET STRING (SIZE (1..32))
		 MAX-ACCESS 	 accessible-for-notify
		 STATUS 	 current
		 DESCRIPTION
		   "URL category associated with the session (if applicable)."
		 ::= { panCommonEventObjs 104}
--
--

	 panTrafficSessionEndReason OBJECT-TYPE
		 SYNTAX 	 OCTET STRING (SIZE (1..32))
		 MAX-ACCESS 	 accessible-for-notify
		 STATUS 	 current
		 DESCRIPTION
		   "Session end reason ."
		 ::= { panCommonEventObjs 105}
--
--

	 panTrafficTunnelID OBJECT-TYPE
		 SYNTAX 	 Counter64
		 MAX-ACCESS 	 accessible-for-notify
		 STATUS 	 current
		 DESCRIPTION
		   "Tunned ID."
		 ::= { panCommonEventObjs 106}
--
--

	 panTrafficImsi OBJECT-TYPE
		 SYNTAX 	 Counter64
		 MAX-ACCESS 	 accessible-for-notify
		 STATUS 	 current
		 DESCRIPTION
		   "IMSI."
		 ::= { panCommonEventObjs 107}
--
--

	 panTrafficMonitorTag OBJECT-TYPE
		 SYNTAX 	 OCTET STRING (SIZE (1..32))
		 MAX-ACCESS 	 accessible-for-notify
		 STATUS 	 current
		 DESCRIPTION
		   "Monitor Tag."
		 ::= { panCommonEventObjs 108}
--
--

	 panTrafficImei OBJECT-TYPE
		 SYNTAX 	 OCTET STRING (SIZE (1..32))
		 MAX-ACCESS 	 accessible-for-notify
		 STATUS 	 current
		 DESCRIPTION
		   "IMEI."
		 ::= { panCommonEventObjs 109}
--
--

	 panTrafficParentSessionId OBJECT-TYPE
		 SYNTAX 	 Counter32
		 MAX-ACCESS 	 accessible-for-notify
		 STATUS 	 current
		 DESCRIPTION
		   "Parent Session ID."
		 ::= { panCommonEventObjs 110}
--
--

	 panTrafficParentStartTime OBJECT-TYPE
		 SYNTAX 	 Counter32
		 MAX-ACCESS 	 accessible-for-notify
		 STATUS 	 current
		 DESCRIPTION
		   "Parent Start Time."
		 ::= { panCommonEventObjs 111}
--
--

	 panTrafficSrcDevCat OBJECT-TYPE
		 SYNTAX 	 OCTET STRING (SIZE (1..64))
		 MAX-ACCESS 	 accessible-for-notify
		 STATUS 	 current
		 DESCRIPTION
		   "Source Device Cateogry."
		 ::= { panCommonEventObjs 112}
--
--

	 panTrafficDstDevCat OBJECT-TYPE
		 SYNTAX 	 OCTET STRING (SIZE (1..64))
		 MAX-ACCESS 	 accessible-for-notify
		 STATUS 	 current
		 DESCRIPTION
		   "Destination Device Cateogry."
		 ::= { panCommonEventObjs 113}
--
--

	 panTrafficSrcDevPro OBJECT-TYPE
		 SYNTAX 	 OCTET STRING (SIZE (1..64))
		 MAX-ACCESS 	 accessible-for-notify
		 STATUS 	 current
		 DESCRIPTION
		   "Source Device Profiles."
		 ::= { panCommonEventObjs 114}
--
--

	 panTrafficDstDevPro OBJECT-TYPE
		 SYNTAX 	 OCTET STRING (SIZE (1..64))
		 MAX-ACCESS 	 accessible-for-notify
		 STATUS 	 current
		 DESCRIPTION
		   "Destination Device Profiles."
		 ::= { panCommonEventObjs 115}
--
--

	 panTrafficSrcDevVen OBJECT-TYPE
		 SYNTAX 	 OCTET STRING (SIZE (1..64))
		 MAX-ACCESS 	 accessible-for-notify
		 STATUS 	 current
		 DESCRIPTION
		   "Source Device Vendor."
		 ::= { panCommonEventObjs 116}
--
--

	 panTrafficDstDevVen OBJECT-TYPE
		 SYNTAX 	 OCTET STRING (SIZE (1..64))
		 MAX-ACCESS 	 accessible-for-notify
		 STATUS 	 current
		 DESCRIPTION
		   "Destination Device Vendor."
		 ::= { panCommonEventObjs 117}
--
--

	 panTrafficSrcDevMod OBJECT-TYPE
		 SYNTAX 	 OCTET STRING (SIZE (1..64))
		 MAX-ACCESS 	 accessible-for-notify
		 STATUS 	 current
		 DESCRIPTION
		   "Source Device Model."
		 ::= { panCommonEventObjs 118}
--
--

	 panTrafficDstDevMod OBJECT-TYPE
		 SYNTAX 	 OCTET STRING (SIZE (1..64))
		 MAX-ACCESS 	 accessible-for-notify
		 STATUS 	 current
		 DESCRIPTION
		   "Destination Device Model."
		 ::= { panCommonEventObjs 119}
--
--

	 panTrafficSrcOSFam OBJECT-TYPE
		 SYNTAX 	 OCTET STRING (SIZE (1..64))
		 MAX-ACCESS 	 accessible-for-notify
		 STATUS 	 current
		 DESCRIPTION
		   "Source Operating System Family."
		 ::= { panCommonEventObjs 120}
--
--

	 panTrafficDstOSFam OBJECT-TYPE
		 SYNTAX 	 OCTET STRING (SIZE (1..64))
		 MAX-ACCESS 	 accessible-for-notify
		 STATUS 	 current
		 DESCRIPTION
		   "Destination Operating System."
		 ::= { panCommonEventObjs 121}
--
--

	 panTrafficSrcOSVer OBJECT-TYPE
		 SYNTAX 	 OCTET STRING (SIZE (1..64))
		 MAX-ACCESS 	 accessible-for-notify
		 STATUS 	 current
		 DESCRIPTION
		   "Source Operating System Version."
		 ::= { panCommonEventObjs 122}
--
--

	 panTrafficDstOSVer OBJECT-TYPE
		 SYNTAX 	 OCTET STRING (SIZE (1..64))
		 MAX-ACCESS 	 accessible-for-notify
		 STATUS 	 current
		 DESCRIPTION
		   "Destination Operating Version."
		 ::= { panCommonEventObjs 123}
--
--

	 panTrafficSrcHost OBJECT-TYPE
		 SYNTAX 	 OCTET STRING (SIZE (1..256))
		 MAX-ACCESS 	 accessible-for-notify
		 STATUS 	 current
		 DESCRIPTION
		   "Source Hostname."
		 ::= { panCommonEventObjs 124}
--
--

	 panTrafficDstHost OBJECT-TYPE
		 SYNTAX 	 OCTET STRING (SIZE (1..256))
		 MAX-ACCESS 	 accessible-for-notify
		 STATUS 	 current
		 DESCRIPTION
		   "Destination Hostname."
		 ::= { panCommonEventObjs 125}
--
--

	 panTrafficSrcMAC OBJECT-TYPE
		 SYNTAX 	 Counter64
		 MAX-ACCESS 	 accessible-for-notify
		 STATUS 	 current
		 DESCRIPTION
		   "Source MAC address."
		 ::= { panCommonEventObjs 126}
--
--

	 panTrafficDstMAC OBJECT-TYPE
		 SYNTAX 	 Counter64
		 MAX-ACCESS 	 accessible-for-notify
		 STATUS 	 current
		 DESCRIPTION
		   "Destination MAC address."
		 ::= { panCommonEventObjs 127}
--
--

	 panConfigCmd OBJECT-TYPE
		 SYNTAX 	 OCTET STRING (SIZE (0..16))
		 MAX-ACCESS 	 accessible-for-notify
		 STATUS 	 current
		 DESCRIPTION
		   "Configuration command."
		 ::= { panCommonEventObjs 150}
--
--

	 panConfigAdmin OBJECT-TYPE
		 SYNTAX 	 OCTET STRING (SIZE (0..32))
		 MAX-ACCESS 	 accessible-for-notify
		 STATUS 	 current
		 DESCRIPTION
		   "Admin name who issued configuration command."
		 ::= { panCommonEventObjs 151}
--
--

	 panConfigClient OBJECT-TYPE
		 SYNTAX 	 OCTET STRING (SIZE (1..16))
		 MAX-ACCESS 	 accessible-for-notify
		 STATUS 	 current
		 DESCRIPTION
		   "Configuration client that generated command."
		 ::= { panCommonEventObjs 152}
--
--

	 panConfigResult OBJECT-TYPE
		 SYNTAX 	 OCTET STRING (SIZE (1..32))
		 MAX-ACCESS 	 accessible-for-notify
		 STATUS 	 current
		 DESCRIPTION
		   "Configuration command execution result success/failure ."
		 ::= { panCommonEventObjs 153}
--
--

	 panConfigPath OBJECT-TYPE
		 SYNTAX 	 OCTET STRING (SIZE (1..255))
		 MAX-ACCESS 	 accessible-for-notify
		 STATUS 	 current
		 DESCRIPTION
		   "Configuration path."
		 ::= { panCommonEventObjs 154}
--
--

	 panThreatId OBJECT-TYPE
		 SYNTAX 	 OCTET STRING (SIZE (1..32))
		 MAX-ACCESS 	 accessible-for-notify
		 STATUS 	 current
		 DESCRIPTION
		   "Palo Alto Networks identifier for the threat. It is a numerical identifier followed by a description in parenthesis for some Subtypes."
		 ::= { panCommonEventObjs 200}
--
--

	 panThreatCategory OBJECT-TYPE
		 SYNTAX 	 OCTET STRING (SIZE (1..32))
		 MAX-ACCESS 	 accessible-for-notify
		 STATUS 	 current
		 DESCRIPTION
		   "Provides URL Category for URL Subtype; For other subtypes the value is 'any'."
		 ::= { panCommonEventObjs 201}
--
--

	 panThreatContentType OBJECT-TYPE
		 SYNTAX 	 OCTET STRING (SIZE (1..32))
		 MAX-ACCESS 	 accessible-for-notify
		 STATUS 	 current
		 DESCRIPTION
		   "Content type of the HTTP response data. Maximum length 32 bytes. Applicable only when Subtype is URL."
		 ::= { panCommonEventObjs 202}
--
--

	 panThreatSeverity OBJECT-TYPE
		 SYNTAX 	 INTEGER { unused (0), informational (1), low (2), medium (3), high (4), critical (5) }
		 MAX-ACCESS 	 accessible-for-notify
		 STATUS 	 current
		 DESCRIPTION
		   "Severity associated with the threat; Values are informational, low, medium, high, critical."
		 ::= { panCommonEventObjs 203}
--
--

	 panThreatDirection OBJECT-TYPE
		 SYNTAX 	 INTEGER { client-to-server(0), server-to-client(1) }
		 MAX-ACCESS 	 accessible-for-notify
		 STATUS 	 current
		 DESCRIPTION
		   "Indicates the direction of the attack, 'client-to-server' or 'server-to-client'."
		 ::= { panCommonEventObjs 204}
--
--

	 panMiscellaneous OBJECT-TYPE
		 SYNTAX 	 OCTET STRING (SIZE (1..1024))
		 MAX-ACCESS 	 accessible-for-notify
		 STATUS 	 current
		 DESCRIPTION
		   "The actual URI when the subtype is URL; File name or file type when the subtype is file; and File name when the subtype is virus."
		 ::= { panCommonEventObjs 205}
--
--

	 panPcapId OBJECT-TYPE
		 SYNTAX 	 Counter64
		 MAX-ACCESS 	 accessible-for-notify
		 STATUS 	 current
		 DESCRIPTION
		   "A 64-bit unsigned integer denoting an ID that correlates threat pcaps with extended pcaps."
		 ::= { panCommonEventObjs 206}
--
--

	 panFileDigest OBJECT-TYPE
		 SYNTAX 	 OCTET STRING (SIZE (1..128))
		 MAX-ACCESS 	 accessible-for-notify
		 STATUS 	 current
		 DESCRIPTION
		   "A hash of the file that was sent to the Wildfire cloud."
		 ::= { panCommonEventObjs 207}
--
--

	 panCloud OBJECT-TYPE
		 SYNTAX 	 OCTET STRING (SIZE (1..1024))
		 MAX-ACCESS 	 accessible-for-notify
		 STATUS 	 current
		 DESCRIPTION
		   "FQDN of the Wildfire cloud that analyzed the file."
		 ::= { panCommonEventObjs 208}
--
--

	 panUrlIndex OBJECT-TYPE
		 SYNTAX 	 INTEGER
		 MAX-ACCESS 	 accessible-for-notify
		 STATUS 	 current
		 DESCRIPTION
		   "Url Index for correlating related logs."
		 ::= { panCommonEventObjs 209}
--
--

	 panUserAgent OBJECT-TYPE
		 SYNTAX 	 OCTET STRING (SIZE (1..256))
		 MAX-ACCESS 	 accessible-for-notify
		 STATUS 	 current
		 DESCRIPTION
		   "User Agent field in HTTP header."
		 ::= { panCommonEventObjs 210}
--
--

	 panXff OBJECT-TYPE
		 SYNTAX 	 OCTET STRING (SIZE (1..128))
		 MAX-ACCESS 	 accessible-for-notify
		 STATUS 	 current
		 DESCRIPTION
		   "X-Forwarded-For field in HTTP header."
		 ::= { panCommonEventObjs 211}
--
--

	 panReferer OBJECT-TYPE
		 SYNTAX 	 OCTET STRING (SIZE (1..1024))
		 MAX-ACCESS 	 accessible-for-notify
		 STATUS 	 current
		 DESCRIPTION
		   "Referer field in HTTP header."
		 ::= { panCommonEventObjs 212}
--
--

	 panSender OBJECT-TYPE
		 SYNTAX 	 OCTET STRING (SIZE (1..256))
		 MAX-ACCESS 	 accessible-for-notify
		 STATUS 	 current
		 DESCRIPTION
		   "Sender field in email header."
		 ::= { panCommonEventObjs 213}
--
--

	 panSubject OBJECT-TYPE
		 SYNTAX 	 OCTET STRING (SIZE (1..256))
		 MAX-ACCESS 	 accessible-for-notify
		 STATUS 	 current
		 DESCRIPTION
		   "Subject field in email header."
		 ::= { panCommonEventObjs 214}
--
--

	 panRecipient OBJECT-TYPE
		 SYNTAX 	 OCTET STRING (SIZE (1..1024))
		 MAX-ACCESS 	 accessible-for-notify
		 STATUS 	 current
		 DESCRIPTION
		   "Recipient field in email header."
		 ::= { panCommonEventObjs 215}
--
--

	 panFileType OBJECT-TYPE
		 SYNTAX 	 OCTET STRING (SIZE (1..32))
		 MAX-ACCESS 	 accessible-for-notify
		 STATUS 	 current
		 DESCRIPTION
		   "File type in WildFire Submissions log."
		 ::= { panCommonEventObjs 216}
--
--

	 panReportId OBJECT-TYPE
		 SYNTAX 	 OCTET STRING (SIZE (1..32))
		 MAX-ACCESS 	 accessible-for-notify
		 STATUS 	 current
		 DESCRIPTION
		   "Palo Alto Networks identifier for the report."
		 ::= { panCommonEventObjs 217}
--
--

	 panHttpMethod OBJECT-TYPE
		 SYNTAX 	 INTEGER
		 MAX-ACCESS 	 accessible-for-notify
		 STATUS 	 current
		 DESCRIPTION
		   "Http method for correlating related logs."
		 ::= { panCommonEventObjs 218}
--
--

	 panThreatTunnelID OBJECT-TYPE
		 SYNTAX 	 Counter64
		 MAX-ACCESS 	 accessible-for-notify
		 STATUS 	 current
		 DESCRIPTION
		   "Tunned ID."
		 ::= { panCommonEventObjs 219}
--
--

	 panThreatImsi OBJECT-TYPE
		 SYNTAX 	 Counter64
		 MAX-ACCESS 	 accessible-for-notify
		 STATUS 	 current
		 DESCRIPTION
		   "IMSI."
		 ::= { panCommonEventObjs 220}
--
--

	 panThreatMonitorTag OBJECT-TYPE
		 SYNTAX 	 OCTET STRING (SIZE (1..32))
		 MAX-ACCESS 	 accessible-for-notify
		 STATUS 	 current
		 DESCRIPTION
		   "Monitor Tag."
		 ::= { panCommonEventObjs 221}
--
--

	 panThreatImei OBJECT-TYPE
		 SYNTAX 	 OCTET STRING (SIZE (1..32))
		 MAX-ACCESS 	 accessible-for-notify
		 STATUS 	 current
		 DESCRIPTION
		   "IMEI."
		 ::= { panCommonEventObjs 222}
--
--

	 panThreatParentSessionId OBJECT-TYPE
		 SYNTAX 	 Counter32
		 MAX-ACCESS 	 accessible-for-notify
		 STATUS 	 current
		 DESCRIPTION
		   "Parent Session ID."
		 ::= { panCommonEventObjs 223}
--
--

	 panThreatParentStartTime OBJECT-TYPE
		 SYNTAX 	 Counter32
		 MAX-ACCESS 	 accessible-for-notify
		 STATUS 	 current
		 DESCRIPTION
		   "Parent Start Time."
		 ::= { panCommonEventObjs 224}
--
--

	 panThrCategory OBJECT-TYPE
		 SYNTAX 	 Counter32
		 MAX-ACCESS 	 accessible-for-notify
		 STATUS 	 current
		 DESCRIPTION
		   "Provides Threat Category."
		 ::= { panCommonEventObjs 225}
--
--

	 panThreatSrcDevCat OBJECT-TYPE
		 SYNTAX 	 OCTET STRING (SIZE (1..64))
		 MAX-ACCESS 	 accessible-for-notify
		 STATUS 	 current
		 DESCRIPTION
		   "Source Device Category."
		 ::= { panCommonEventObjs 226}
--
--

	 panThreatDstDevCat OBJECT-TYPE
		 SYNTAX 	 OCTET STRING (SIZE (1..64))
		 MAX-ACCESS 	 accessible-for-notify
		 STATUS 	 current
		 DESCRIPTION
		   "Destination Device Category."
		 ::= { panCommonEventObjs 227}
--
--

	 panThreatSrcDevPro OBJECT-TYPE
		 SYNTAX 	 OCTET STRING (SIZE (1..64))
		 MAX-ACCESS 	 accessible-for-notify
		 STATUS 	 current
		 DESCRIPTION
		   "Source Device Profile."
		 ::= { panCommonEventObjs 228}
--
--

	 panThreatDstDevPro OBJECT-TYPE
		 SYNTAX 	 OCTET STRING (SIZE (1..64))
		 MAX-ACCESS 	 accessible-for-notify
		 STATUS 	 current
		 DESCRIPTION
		   "Destination Device Profile."
		 ::= { panCommonEventObjs 229}
--
--

	 panThreatSrcDevVen OBJECT-TYPE
		 SYNTAX 	 OCTET STRING (SIZE (1..64))
		 MAX-ACCESS 	 accessible-for-notify
		 STATUS 	 current
		 DESCRIPTION
		   "Source Device Vendor."
		 ::= { panCommonEventObjs 230}
--
--

	 panThreatDstDevVen OBJECT-TYPE
		 SYNTAX 	 OCTET STRING (SIZE (1..64))
		 MAX-ACCESS 	 accessible-for-notify
		 STATUS 	 current
		 DESCRIPTION
		   "Destination Device Vendor."
		 ::= { panCommonEventObjs 231}
--
--

	 panThreatSrcDevMod OBJECT-TYPE
		 SYNTAX 	 OCTET STRING (SIZE (1..64))
		 MAX-ACCESS 	 accessible-for-notify
		 STATUS 	 current
		 DESCRIPTION
		   "Source Device Model."
		 ::= { panCommonEventObjs 232}
--
--

	 panThreatDstDevMod OBJECT-TYPE
		 SYNTAX 	 OCTET STRING (SIZE (1..64))
		 MAX-ACCESS 	 accessible-for-notify
		 STATUS 	 current
		 DESCRIPTION
		   "Destination Device Model."
		 ::= { panCommonEventObjs 233}
--
--

	 panThreatSrcOSFam OBJECT-TYPE
		 SYNTAX 	 OCTET STRING (SIZE (1..64))
		 MAX-ACCESS 	 accessible-for-notify
		 STATUS 	 current
		 DESCRIPTION
		   "Source Operating System Family."
		 ::= { panCommonEventObjs 234}
--
--

	 panThreatDstOSFam OBJECT-TYPE
		 SYNTAX 	 OCTET STRING (SIZE (1..64))
		 MAX-ACCESS 	 accessible-for-notify
		 STATUS 	 current
		 DESCRIPTION
		   "Destination Operating System Family."
		 ::= { panCommonEventObjs 235}
--
--

	 panThreatSrcOSVer OBJECT-TYPE
		 SYNTAX 	 OCTET STRING (SIZE (1..64))
		 MAX-ACCESS 	 accessible-for-notify
		 STATUS 	 current
		 DESCRIPTION
		   "Source Operating System Version."
		 ::= { panCommonEventObjs 236}
--
--

	 panThreatDstOSVer OBJECT-TYPE
		 SYNTAX 	 OCTET STRING (SIZE (1..64))
		 MAX-ACCESS 	 accessible-for-notify
		 STATUS 	 current
		 DESCRIPTION
		   "Destination Operating System Version."
		 ::= { panCommonEventObjs 237}
--
--

	 panThreatSrcHost OBJECT-TYPE
		 SYNTAX 	 OCTET STRING (SIZE (1..256))
		 MAX-ACCESS 	 accessible-for-notify
		 STATUS 	 current
		 DESCRIPTION
		   "Source Hostname."
		 ::= { panCommonEventObjs 238}
--
--

	 panThreatDstHost OBJECT-TYPE
		 SYNTAX 	 OCTET STRING (SIZE (1..256))
		 MAX-ACCESS 	 accessible-for-notify
		 STATUS 	 current
		 DESCRIPTION
		   "Destination Hostname."
		 ::= { panCommonEventObjs 239}
--
--

	 panThreatSrcMAC OBJECT-TYPE
		 SYNTAX 	 Counter64
		 MAX-ACCESS 	 accessible-for-notify
		 STATUS 	 current
		 DESCRIPTION
		   "Source MAC address."
		 ::= { panCommonEventObjs 240}
--
--

	 panThreatDstMAC OBJECT-TYPE
		 SYNTAX 	 Counter64
		 MAX-ACCESS 	 accessible-for-notify
		 STATUS 	 current
		 DESCRIPTION
		   "Destination MAC address."
		 ::= { panCommonEventObjs 241}
--
--

	 panThreatCloudReportId OBJECT-TYPE
		 SYNTAX 	 OCTET STRING (SIZE (1..128))
		 MAX-ACCESS 	 accessible-for-notify
		 STATUS 	 current
		 DESCRIPTION
		   "Cloud Report ID."
		 ::= { panCommonEventObjs 242}
--
--

	 panHipSourceUser OBJECT-TYPE
		 SYNTAX 	 OCTET STRING (SIZE (1..64))
		 MAX-ACCESS 	 accessible-for-notify
		 STATUS 	 current
		 DESCRIPTION
		   "User name of the Source user."
		 ::= { panCommonEventObjs 250}
--
--

	 panHipMachineName OBJECT-TYPE
		 SYNTAX 	 OCTET STRING (SIZE (1..256))
		 MAX-ACCESS 	 accessible-for-notify
		 STATUS 	 current
		 DESCRIPTION
		   "Name of the Users machine."
		 ::= { panCommonEventObjs 251}
--
--

	 panHipSourceAddr OBJECT-TYPE
		 SYNTAX 	 IpAddress
		 MAX-ACCESS 	 accessible-for-notify
		 STATUS 	 current
		 DESCRIPTION
		   "HIP Match source IP. This field is deprecated.
			Please use panHipSourceInetAddrType and panHipSourceInetAddr."
		 ::= { panCommonEventObjs 252}
--
--

	 panHipMatch OBJECT-TYPE
		 SYNTAX 	 OCTET STRING (SIZE (1..32))
		 MAX-ACCESS 	 accessible-for-notify
		 STATUS 	 current
		 DESCRIPTION
		   "Name of the HIP Object or Profile."
		 ::= { panCommonEventObjs 253}
--
--

	 panHipMatchType OBJECT-TYPE
		 SYNTAX 	 OCTET STRING (SIZE (1..32))
		 MAX-ACCESS 	 accessible-for-notify
		 STATUS 	 current
		 DESCRIPTION
		   "Specifies whether the HIP field represents a HIP Object or a HIP Profile."
		 ::= { panCommonEventObjs 254}
--
--

	 panHipRepeatCount OBJECT-TYPE
		 SYNTAX 	 Counter32
		 MAX-ACCESS 	 accessible-for-notify
		 STATUS 	 current
		 DESCRIPTION
		   "Number of times the HIP profile matched."
		 ::= { panCommonEventObjs 255}
--
--

	 panHipOS OBJECT-TYPE
		 SYNTAX 	 OCTET STRING (SIZE (1..32))
		 MAX-ACCESS 	 accessible-for-notify
		 STATUS 	 current
		 DESCRIPTION
		   "String representing the operating system of the client."
		 ::= { panCommonEventObjs 256}
--
--

	 panHipSourceInetAddrType OBJECT-TYPE
		 SYNTAX 	 InetAddressType
		 MAX-ACCESS 	 accessible-for-notify
		 STATUS 	 current
		 DESCRIPTION
		   "HIP Match source IP type"
		 ::= { panCommonEventObjs 257}
--
--

	 panHipSourceInetAddr OBJECT-TYPE
		 SYNTAX 	 InetAddress
		 MAX-ACCESS 	 accessible-for-notify
		 STATUS 	 current
		 DESCRIPTION
		   "HIP Match source IP"
		 ::= { panCommonEventObjs 258}
--
--

	 panHipSourceIPv6 OBJECT-TYPE
		 SYNTAX 	 IpAddress
		 MAX-ACCESS 	 accessible-for-notify
		 STATUS 	 current
		 DESCRIPTION
		   "HIP Match source IPv6. This field is deprecated.
			Please use panHipSourceInetAddrType and panHipSourceInetAddr."
		 ::= { panCommonEventObjs 259}
--
--

	 panHipSourceIPv6InetAddrType OBJECT-TYPE
		 SYNTAX 	 InetAddressType
		 MAX-ACCESS 	 accessible-for-notify
		 STATUS 	 current
		 DESCRIPTION
		   "HIP Match source IPv6 type"
		 ::= { panCommonEventObjs 260}
--
--

	 panHipSourceIPv6InetAddr OBJECT-TYPE
		 SYNTAX 	 InetAddress
		 MAX-ACCESS 	 accessible-for-notify
		 STATUS 	 current
		 DESCRIPTION
		   "HIP Match source IPv6"
		 ::= { panCommonEventObjs 261}
--
--

	 panHipMAC OBJECT-TYPE
		 SYNTAX 	 Counter64
		 MAX-ACCESS 	 accessible-for-notify
		 STATUS 	 current
		 DESCRIPTION
		   "HIP Match Device MAC address"
		 ::= { panCommonEventObjs 262}
--
--

	 panSystemEventId OBJECT-TYPE
		 SYNTAX 	 OCTET STRING (SIZE (1..32))
		 MAX-ACCESS 	 accessible-for-notify
		 STATUS 	 current
		 DESCRIPTION
		   "System log event ID"
		 ::= { panCommonEventObjs 300}
--
--

	 panSystemObject OBJECT-TYPE
		 SYNTAX 	 OCTET STRING (SIZE (1..32))
		 MAX-ACCESS 	 accessible-for-notify
		 STATUS 	 current
		 DESCRIPTION
		   "System log event object"
		 ::= { panCommonEventObjs 301}
--
--

	 panSystemModule OBJECT-TYPE
		 SYNTAX 	 OCTET STRING (SIZE (1..16))
		 MAX-ACCESS 	 accessible-for-notify
		 STATUS 	 current
		 DESCRIPTION
		   "System log event module"
		 ::= { panCommonEventObjs 302}
--
--

	 panSystemSeverity OBJECT-TYPE
		 SYNTAX 	 INTEGER { unused (0), informational (1), low (2), medium (3), high (4), critical (5) }
		 MAX-ACCESS 	 accessible-for-notify
		 STATUS 	 current
		 DESCRIPTION
		   "System log event severity"
		 ::= { panCommonEventObjs 303}
--
--

	 panSystemDescription OBJECT-TYPE
		 SYNTAX 	 OCTET STRING (SIZE (1..512))
		 MAX-ACCESS 	 accessible-for-notify
		 STATUS 	 current
		 DESCRIPTION
		   "System log event description"
		 ::= { panCommonEventObjs 304}
--
--

	 panCorrDG1 OBJECT-TYPE
		 SYNTAX 	 OCTET STRING (SIZE (1..32))
		 MAX-ACCESS 	 accessible-for-notify
		 STATUS 	 current
		 DESCRIPTION
		   "Correlation log DG Heirarchy 1"
		 ::= { panCommonEventObjs 350}
--
--

	 panCorrDG2 OBJECT-TYPE
		 SYNTAX 	 OCTET STRING (SIZE (1..32))
		 MAX-ACCESS 	 accessible-for-notify
		 STATUS 	 current
		 DESCRIPTION
		   "Correlation log DG Heirarchy 2"
		 ::= { panCommonEventObjs 351}
--
--

	 panCorrDG3 OBJECT-TYPE
		 SYNTAX 	 OCTET STRING (SIZE (1..32))
		 MAX-ACCESS 	 accessible-for-notify
		 STATUS 	 current
		 DESCRIPTION
		   "Correlation log DG Heirarchy 3"
		 ::= { panCommonEventObjs 352}
--
--

	 panCorrDG4 OBJECT-TYPE
		 SYNTAX 	 OCTET STRING (SIZE (1..32))
		 MAX-ACCESS 	 accessible-for-notify
		 STATUS 	 current
		 DESCRIPTION
		   "Correlation log DG Heirarchy 4"
		 ::= { panCommonEventObjs 353}
--
--

	 panCorrObjName OBJECT-TYPE
		 SYNTAX 	 OCTET STRING (SIZE (1..32))
		 MAX-ACCESS 	 accessible-for-notify
		 STATUS 	 current
		 DESCRIPTION
		   "Correlation log Object Name"
		 ::= { panCommonEventObjs 354}
--
--

	 panCorrObjID OBJECT-TYPE
		 SYNTAX 	 INTEGER
		 MAX-ACCESS 	 accessible-for-notify
		 STATUS 	 current
		 DESCRIPTION
		   "Correlation log Object ID"
		 ::= { panCommonEventObjs 355}
--
--

	 panCorrSeverity OBJECT-TYPE
		 SYNTAX 	 INTEGER
		 MAX-ACCESS 	 accessible-for-notify
		 STATUS 	 current
		 DESCRIPTION
		   "Correlation log event severity"
		 ::= { panCommonEventObjs 356}
--
--

	 panCorrEvidence OBJECT-TYPE
		 SYNTAX 	 OCTET STRING (SIZE (1..1024))
		 MAX-ACCESS 	 accessible-for-notify
		 STATUS 	 current
		 DESCRIPTION
		   "Correlation log Evidence"
		 ::= { panCommonEventObjs 357}
--
--

	 panGtpTunnelID OBJECT-TYPE
		 SYNTAX 	 Counter64
		 MAX-ACCESS 	 accessible-for-notify
		 STATUS 	 current
		 DESCRIPTION
		   "Tunned ID."
		 ::= { panCommonEventObjs 400}
--
--

	 panGtpImsi OBJECT-TYPE
		 SYNTAX 	 Counter64
		 MAX-ACCESS 	 accessible-for-notify
		 STATUS 	 current
		 DESCRIPTION
		   "IMSI."
		 ::= { panCommonEventObjs 401}
--
--

	 panGtpMonitorTag OBJECT-TYPE
		 SYNTAX 	 OCTET STRING (SIZE (1..32))
		 MAX-ACCESS 	 accessible-for-notify
		 STATUS 	 current
		 DESCRIPTION
		   "Monitor Tag."
		 ::= { panCommonEventObjs 402}
--
--

	 panGtpImei OBJECT-TYPE
		 SYNTAX 	 OCTET STRING (SIZE (1..32))
		 MAX-ACCESS 	 accessible-for-notify
		 STATUS 	 current
		 DESCRIPTION
		   "IMEI."
		 ::= { panCommonEventObjs 403}
--
--

	 panGtpParentSessionId OBJECT-TYPE
		 SYNTAX 	 Counter32
		 MAX-ACCESS 	 accessible-for-notify
		 STATUS 	 current
		 DESCRIPTION
		   "Parent Session ID."
		 ::= { panCommonEventObjs 404}
--
--

	 panGtpParentStartTime OBJECT-TYPE
		 SYNTAX 	 Counter32
		 MAX-ACCESS 	 accessible-for-notify
		 STATUS 	 current
		 DESCRIPTION
		   "Parent Start Time."
		 ::= { panCommonEventObjs 405}
--
--

	 panGtpMsisdn OBJECT-TYPE
		 SYNTAX 	 OCTET STRING (SIZE (1..16))
		 MAX-ACCESS 	 accessible-for-notify
		 STATUS 	 current
		 DESCRIPTION
		   "Mobile Subscriber ISDN Number (MSISDN)."
		 ::= { panCommonEventObjs 406}
--
--

	 panGtpApn OBJECT-TYPE
		 SYNTAX 	 OCTET STRING (SIZE (1..128))
		 MAX-ACCESS 	 accessible-for-notify
		 STATUS 	 current
		 DESCRIPTION
		   "Access point name (APN)."
		 ::= { panCommonEventObjs 407}
--
--

	 panGtpRat OBJECT-TYPE
		 SYNTAX 	 OCTET STRING (SIZE (1..16))
		 MAX-ACCESS 	 accessible-for-notify
		 STATUS 	 current
		 DESCRIPTION
		   "RAT."
		 ::= { panCommonEventObjs 408}
--
--

	 panGtpMsgType OBJECT-TYPE
		 SYNTAX 	 OCTET STRING (SIZE (1..64))
		 MAX-ACCESS 	 accessible-for-notify
		 STATUS 	 current
		 DESCRIPTION
		   "Message Type."
		 ::= { panCommonEventObjs 409}
--
--

	 panGtpEndipaddrInetAddrType OBJECT-TYPE
		 SYNTAX 	 InetAddressType
		 MAX-ACCESS 	 accessible-for-notify
		 STATUS 	 current
		 DESCRIPTION
		   "Original session source IP address type"
		 ::= { panCommonEventObjs 410}
--
--

	 panGtpEndIpAddr OBJECT-TYPE
		 SYNTAX 	 InetAddress
		 MAX-ACCESS 	 accessible-for-notify
		 STATUS 	 current
		 DESCRIPTION
		   "Original session source IP address."
		 ::= { panCommonEventObjs 411}
--
--

	 panGtpTeid1 OBJECT-TYPE
		 SYNTAX 	 Counter32
		 MAX-ACCESS 	 accessible-for-notify
		 STATUS 	 current
		 DESCRIPTION
		   "Teid1."
		 ::= { panCommonEventObjs 412}
--
--

	 panGtpTeid2 OBJECT-TYPE
		 SYNTAX 	 Counter32
		 MAX-ACCESS 	 accessible-for-notify
		 STATUS 	 current
		 DESCRIPTION
		   "Teid2."
		 ::= { panCommonEventObjs 413}
--
--

	 panGtpInterface OBJECT-TYPE
		 SYNTAX 	 OCTET STRING (SIZE (1..16))
		 MAX-ACCESS 	 accessible-for-notify
		 STATUS 	 current
		 DESCRIPTION
		   "GTP interface."
		 ::= { panCommonEventObjs 414}
--
--

	 panGtpCauseCode OBJECT-TYPE
		 SYNTAX 	 OCTET STRING (SIZE (1..32))
		 MAX-ACCESS 	 accessible-for-notify
		 STATUS 	 current
		 DESCRIPTION
		   "GTP Cause Code."
		 ::= { panCommonEventObjs 415}
--
--

	 panGtpEventType OBJECT-TYPE
		 SYNTAX 	 OCTET STRING (SIZE (1..64))
		 MAX-ACCESS 	 accessible-for-notify
		 STATUS 	 current
		 DESCRIPTION
		   "GTP Event Type."
		 ::= { panCommonEventObjs 416}
--
--

	 panGtpSeverity OBJECT-TYPE
		 SYNTAX 	 INTEGER { unused (0), informational (1), low (2), medium (3), high (4), critical (5) }
		 MAX-ACCESS 	 accessible-for-notify
		 STATUS 	 current
		 DESCRIPTION
		   "Severity associated with the gtp; Values are informational, low, medium, high, critical."
		 ::= { panCommonEventObjs 417}
--
--

	 panGtpMcc OBJECT-TYPE
		 SYNTAX 	 Counter32
		 MAX-ACCESS 	 accessible-for-notify
		 STATUS 	 current
		 DESCRIPTION
		   "Mobile country code."
		 ::= { panCommonEventObjs 418}
--
--

	 panGtpMnc OBJECT-TYPE
		 SYNTAX 	 Counter32
		 MAX-ACCESS 	 accessible-for-notify
		 STATUS 	 current
		 DESCRIPTION
		   "Mobile network code."
		 ::= { panCommonEventObjs 419}
--
--

	 panGtpAreaCode OBJECT-TYPE
		 SYNTAX 	 Counter32
		 MAX-ACCESS 	 accessible-for-notify
		 STATUS 	 current
		 DESCRIPTION
		   "Area code."
		 ::= { panCommonEventObjs 420}
--
--

	 panGtpCellId OBJECT-TYPE
		 SYNTAX 	 Counter32
		 MAX-ACCESS 	 accessible-for-notify
		 STATUS 	 current
		 DESCRIPTION
		   "Cell id."
		 ::= { panCommonEventObjs 421}
--
--

	 panGtpEventCode OBJECT-TYPE
		 SYNTAX 	 Counter32
		 MAX-ACCESS 	 accessible-for-notify
		 STATUS 	 current
		 DESCRIPTION
		   "Eevent code."
		 ::= { panCommonEventObjs 422}
--
--

	 panGtpBytes OBJECT-TYPE
		 SYNTAX 	 Counter64
		 MAX-ACCESS 	 accessible-for-notify
		 STATUS 	 current
		 DESCRIPTION
		   "Number of total bytes (transmit and receive) for the session."
		 ::= { panCommonEventObjs 423}
--
--

	 panGtpPackets OBJECT-TYPE
		 SYNTAX 	 Counter32
		 MAX-ACCESS 	 accessible-for-notify
		 STATUS 	 current
		 DESCRIPTION
		   "Number of total packets (transmit and receive) for the session."
		 ::= { panCommonEventObjs 424}
--
--

	 panGtpMaxEncap OBJECT-TYPE
		 SYNTAX 	 Counter32
		 MAX-ACCESS 	 accessible-for-notify
		 STATUS 	 current
		 DESCRIPTION
		   "Packets dropped due to maximum encapsulation level reached."
		 ::= { panCommonEventObjs 425}
--
--

	 panGtpUnknownProto OBJECT-TYPE
		 SYNTAX 	 Counter32
		 MAX-ACCESS 	 accessible-for-notify
		 STATUS 	 current
		 DESCRIPTION
		   "Packets dropped due to unknown protocol seen."
		 ::= { panCommonEventObjs 426}
--
--

	 panGtpStrictCheck OBJECT-TYPE
		 SYNTAX 	 Counter32
		 MAX-ACCESS 	 accessible-for-notify
		 STATUS 	 current
		 DESCRIPTION
		   "Packets dropped due to failure to meet RFC strict header checking."
		 ::= { panCommonEventObjs 427}
--
--

	 panGtpTunnelFragment OBJECT-TYPE
		 SYNTAX 	 Counter32
		 MAX-ACCESS 	 accessible-for-notify
		 STATUS 	 current
		 DESCRIPTION
		   "Packets dropped due to fragmentation errors."
		 ::= { panCommonEventObjs 428}
--
--

	 panGtpSessionsCreated OBJECT-TYPE
		 SYNTAX 	 Counter32
		 MAX-ACCESS 	 accessible-for-notify
		 STATUS 	 current
		 DESCRIPTION
		   "Number of inner sessions created for time duration."
		 ::= { panCommonEventObjs 429}
--
--

	 panGtpSessionsClosed OBJECT-TYPE
		 SYNTAX 	 Counter32
		 MAX-ACCESS 	 accessible-for-notify
		 STATUS 	 current
		 DESCRIPTION
		   "Number of completed closed/ended inner sessions for time duration."
		 ::= { panCommonEventObjs 430}
--
--

	 panGtpSessionEndReason OBJECT-TYPE
		 SYNTAX 	 OCTET STRING (SIZE (1..32))
		 MAX-ACCESS 	 accessible-for-notify
		 STATUS 	 current
		 DESCRIPTION
		   "Session end reason."
		 ::= { panCommonEventObjs 431}
--
--

	 panGtpActionSource OBJECT-TYPE
		 SYNTAX 	 OCTET STRING (SIZE (1..32))
		 MAX-ACCESS 	 accessible-for-notify
		 STATUS 	 current
		 DESCRIPTION
		   "Action source."
		 ::= { panCommonEventObjs 432}
--
--

	 panGtpStartTime OBJECT-TYPE
		 SYNTAX 	 OCTET STRING (SIZE (1..32))
		 MAX-ACCESS 	 accessible-for-notify
		 STATUS 	 current
		 DESCRIPTION
		   "Time of session start."
		 ::= { panCommonEventObjs 433}
--
--

	 panGtpElapsed OBJECT-TYPE
		 SYNTAX 	 TimeStamp
		 MAX-ACCESS 	 accessible-for-notify
		 STATUS 	 current
		 DESCRIPTION
		   "Elapsed time of the session."
		 ::= { panCommonEventObjs 434}
--
--

	 panGtpTCIRule OBJECT-TYPE
		 SYNTAX 	 OCTET STRING (SIZE (1..64))
		 MAX-ACCESS 	 accessible-for-notify
		 STATUS 	 current
		 DESCRIPTION
		   "Name of the tunnel content inspection rule that the session matched."
		 ::= { panCommonEventObjs 435}
--
--

	 panGtpRemoteUserIpInetAddrType OBJECT-TYPE
		 SYNTAX 	 InetAddressType
		 MAX-ACCESS 	 accessible-for-notify
		 STATUS 	 current
		 DESCRIPTION
		   "Remote User IP address type for GTP IoT"
		 ::= { panCommonEventObjs 436}
--
--

	 panGtpRemoteUserIp OBJECT-TYPE
		 SYNTAX 	 InetAddress
		 MAX-ACCESS 	 accessible-for-notify
		 STATUS 	 current
		 DESCRIPTION
		   "Remote User IP address for GTP IoT."
		 ::= { panCommonEventObjs 437}
--
--

	 panGtpRemoteUserId OBJECT-TYPE
		 SYNTAX 	 Counter64
		 MAX-ACCESS 	 accessible-for-notify
		 STATUS 	 current
		 DESCRIPTION
		   "Remote User ID for GTP IoT."
		 ::= { panCommonEventObjs 438}
--
--

	 panUseridSourceInetAddrType OBJECT-TYPE
		 SYNTAX 	 InetAddressType
		 MAX-ACCESS 	 accessible-for-notify
		 STATUS 	 current
		 DESCRIPTION
		   "Original session source IP address type"
		 ::= { panCommonEventObjs 500}
--
--

	 panUseridSourceInetAddr OBJECT-TYPE
		 SYNTAX 	 InetAddress
		 MAX-ACCESS 	 accessible-for-notify
		 STATUS 	 current
		 DESCRIPTION
		   "Original session source IP address."
		 ::= { panCommonEventObjs 501}
--
--

	 panUseridUser OBJECT-TYPE
		 SYNTAX 	 OCTET STRING (SIZE (1..64))
		 MAX-ACCESS 	 accessible-for-notify
		 STATUS 	 current
		 DESCRIPTION
		   "UserName"
		 ::= { panCommonEventObjs 502}
--
--

	 panUseridDataSourceName OBJECT-TYPE
		 SYNTAX 	 OCTET STRING (SIZE (1..64))
		 MAX-ACCESS 	 accessible-for-notify
		 STATUS 	 current
		 DESCRIPTION
		   "DataSourceName"
		 ::= { panCommonEventObjs 503}
--
--

	 panUseridEventID OBJECT-TYPE
		 SYNTAX 	 Counter32
		 MAX-ACCESS 	 accessible-for-notify
		 STATUS 	 current
		 DESCRIPTION
		   "Event ID"
		 ::= { panCommonEventObjs 504}
--
--

	 panUseridRepeatCount OBJECT-TYPE
		 SYNTAX 	 Counter32
		 MAX-ACCESS 	 accessible-for-notify
		 STATUS 	 current
		 DESCRIPTION
		   "Number of times the Userid profile matched."
		 ::= { panCommonEventObjs 505}
--
--

	 panUseridTimeout OBJECT-TYPE
		 SYNTAX 	 Counter32
		 MAX-ACCESS 	 accessible-for-notify
		 STATUS 	 current
		 DESCRIPTION
		   "Timeout"
		 ::= { panCommonEventObjs 506}
--
--

	 panUseridBeginport OBJECT-TYPE
		 SYNTAX 	 Counter32
		 MAX-ACCESS 	 accessible-for-notify
		 STATUS 	 current
		 DESCRIPTION
		   "Begin port"
		 ::= { panCommonEventObjs 507}
--
--

	 panUseridEndport OBJECT-TYPE
		 SYNTAX 	 Counter32
		 MAX-ACCESS 	 accessible-for-notify
		 STATUS 	 current
		 DESCRIPTION
		   "End port"
		 ::= { panCommonEventObjs 508}
--
--

	 panUseridDataSource OBJECT-TYPE
		 SYNTAX 	 INTEGER { unknown (0), agent (1), tsAgent (2), eventLog (3), probing (4), serverSessionMonitor (5), captivePortal (6), vpnClient (7), xmlApi (8), ha (9), activeDirectory (10), eDirectory (11), syslog (12) }
		 MAX-ACCESS 	 accessible-for-notify
		 STATUS 	 current
		 DESCRIPTION
		   "Types of DataSource; Values are unknown, agent, tsAgent, eventLog, probing, serverSessionMonitor, captivePortal, vpnClient, xmlApi, ha, activeDirectory, eDirectory, syslog."
		 ::= { panCommonEventObjs 509}
--
--

	 panUseridDataSourceType OBJECT-TYPE
		 SYNTAX 	 INTEGER { unknown (0), directoryServer (1), exchangeServer (2), edirectoryServer (3), wmiProbing (4), netbiosProbing (5), clientCert (6), sso (7), kerbos (8), authenticate (9), globalprotect (10), vpnClient (11) }
		 MAX-ACCESS 	 accessible-for-notify
		 STATUS 	 current
		 DESCRIPTION
		   "Types of DataSource subype; Values are unknown, directoryServer, exchangeServer, edirectoryServer, wmiProbing, clientCert, sso, kerbos, authenticate, globalprotect, vpnClient."
		 ::= { panCommonEventObjs 510}
--
--

	 panUseridFactorType OBJECT-TYPE
		 SYNTAX 	 OCTET STRING (SIZE (1..32))
		 MAX-ACCESS 	 accessible-for-notify
		 STATUS 	 current
		 DESCRIPTION
		   "Factor Type"
		 ::= { panCommonEventObjs 511}
--
--

	 panUseridFactorTime OBJECT-TYPE
		 SYNTAX 	 OCTET STRING (SIZE (1..32))
		 MAX-ACCESS 	 accessible-for-notify
		 STATUS 	 current
		 DESCRIPTION
		   "Time the factor was completed."
		 ::= { panCommonEventObjs 512}
--
--

	 panUseridFactorNo OBJECT-TYPE
		 SYNTAX 	 Counter32
		 MAX-ACCESS 	 accessible-for-notify
		 STATUS 	 current
		 DESCRIPTION
		   "Factor Number"
		 ::= { panCommonEventObjs 513}
--
--

	 panAuthSourceInetAddrType OBJECT-TYPE
		 SYNTAX 	 InetAddressType
		 MAX-ACCESS 	 accessible-for-notify
		 STATUS 	 current
		 DESCRIPTION
		   "Original session source IP address type"
		 ::= { panCommonEventObjs 600}
--
--

	 panAuthSourceInetAddr OBJECT-TYPE
		 SYNTAX 	 InetAddress
		 MAX-ACCESS 	 accessible-for-notify
		 STATUS 	 current
		 DESCRIPTION
		   "Original session source IP address."
		 ::= { panCommonEventObjs 601}
--
--

	 panAuthUser OBJECT-TYPE
		 SYNTAX 	 OCTET STRING (SIZE (1..256))
		 MAX-ACCESS 	 accessible-for-notify
		 STATUS 	 current
		 DESCRIPTION
		   "UserName"
		 ::= { panCommonEventObjs 602}
--
--

	 panAuthNormalizeUser OBJECT-TYPE
		 SYNTAX 	 OCTET STRING (SIZE (1..256))
		 MAX-ACCESS 	 accessible-for-notify
		 STATUS 	 current
		 DESCRIPTION
		   "Normalize UserName"
		 ::= { panCommonEventObjs 603}
--
--

	 panAuthObject OBJECT-TYPE
		 SYNTAX 	 OCTET STRING (SIZE (1..32))
		 MAX-ACCESS 	 accessible-for-notify
		 STATUS 	 current
		 DESCRIPTION
		   "Authentication Object."
		 ::= { panCommonEventObjs 604}
--
--

	 panAuthPolicy OBJECT-TYPE
		 SYNTAX 	 OCTET STRING (SIZE (1..32))
		 MAX-ACCESS 	 accessible-for-notify
		 STATUS 	 current
		 DESCRIPTION
		   "Authentication Policy"
		 ::= { panCommonEventObjs 605}
--
--

	 panAuthRepeatCount OBJECT-TYPE
		 SYNTAX 	 Counter32
		 MAX-ACCESS 	 accessible-for-notify
		 STATUS 	 current
		 DESCRIPTION
		   "Number of times the Userid profile matched."
		 ::= { panCommonEventObjs 606}
--
--

	 panAuthID OBJECT-TYPE
		 SYNTAX 	 Counter64
		 MAX-ACCESS 	 accessible-for-notify
		 STATUS 	 current
		 DESCRIPTION
		   "Authentication ID"
		 ::= { panCommonEventObjs 607}
--
--

	 panAuthVendor OBJECT-TYPE
		 SYNTAX 	 OCTET STRING (SIZE (1..32))
		 MAX-ACCESS 	 accessible-for-notify
		 STATUS 	 current
		 DESCRIPTION
		   "Authentication Vendor"
		 ::= { panCommonEventObjs 608}
--
--

	 panAuthLogForwardingProfile OBJECT-TYPE
		 SYNTAX 	 OCTET STRING (SIZE (1..32))
		 MAX-ACCESS 	 accessible-for-notify
		 STATUS 	 current
		 DESCRIPTION
		   "Log Forwarding Profile that was applied to the session"
		 ::= { panCommonEventObjs 609}
--
--

	 panAuthClientType OBJECT-TYPE
		 SYNTAX 	 INTEGER { adminui (0), cli (1), globalprotectPortal (2), globalprotectGateway (3), clientlessVpn (4), authenticationPortal (5) }
		 MAX-ACCESS 	 accessible-for-notify
		 STATUS 	 current
		 DESCRIPTION
		   "Types of client; Values are admin ui, cli, globalprotect portal, globalprotect gateway, clientless vpn, authentication portal."
		 ::= { panCommonEventObjs 610}
--
--

	 panAuthDescription OBJECT-TYPE
		 SYNTAX 	 OCTET STRING (SIZE (1..512))
		 MAX-ACCESS 	 accessible-for-notify
		 STATUS 	 current
		 DESCRIPTION
		   "Authentication log event description"
		 ::= { panCommonEventObjs 611}
--
--

	 panAuthServerProfile OBJECT-TYPE
		 SYNTAX 	 OCTET STRING (SIZE (1..32))
		 MAX-ACCESS 	 accessible-for-notify
		 STATUS 	 current
		 DESCRIPTION
		   "Authentication Server Profile"
		 ::= { panCommonEventObjs 612}
--
--

	 panAuthEvent OBJECT-TYPE
		 SYNTAX 	 INTEGER { success (0), failure (1), userPasswordFailure (2), userIsLocked (3), userNotAllowed (4), invalidCertificate (5), passwordExpired (6), kerberosSingleSignOnFailed (7), samlSingleSignOnFailed (8), mfaFailed (9), timeout (10) }
		 MAX-ACCESS 	 accessible-for-notify
		 STATUS 	 current
		 DESCRIPTION
		   "Types of event; Values are success, failure, userPasswordFailure, user is locked, userNotAllowed, invalidCertificate, passwordExpired, kerberosSingleSignOnFailed, samlSingleSignOnFailed, mfaFailedAndTimeout."
		 ::= { panCommonEventObjs 613}
--
--

	 panAuthFactorNo OBJECT-TYPE
		 SYNTAX 	 Counter32
		 MAX-ACCESS 	 accessible-for-notify
		 STATUS 	 current
		 DESCRIPTION
		   "Factor Number"
		 ::= { panCommonEventObjs 614}
--
--

	 panAuthProto OBJECT-TYPE
		 SYNTAX 	 INTEGER { peapWithEapGtc (0), peapMschapv2 (1), ttlsPap (2), pap (3), chap (4) }
		 MAX-ACCESS 	 accessible-for-notify
		 STATUS 	 current
		 DESCRIPTION
		   "Types of authentication Protocols: peapWithEapGtc, peapMschapv2, ttlsPap, pap, chap"
		 ::= { panCommonEventObjs 615}
--
--

	 panSctpAssocId OBJECT-TYPE
		 SYNTAX 	 Counter64
		 MAX-ACCESS 	 accessible-for-notify
		 STATUS 	 current
		 DESCRIPTION
		   "SCTP Association ID."
		 ::= { panCommonEventObjs 700}
--
--

	 panSctpPpid OBJECT-TYPE
		 SYNTAX 	 OCTET STRING (SIZE (1..16))
		 MAX-ACCESS 	 accessible-for-notify
		 STATUS 	 current
		 DESCRIPTION
		   "Payload Protocol ID."
		 ::= { panCommonEventObjs 701}
--
--

	 panSctpSeverity OBJECT-TYPE
		 SYNTAX 	 INTEGER { unused (0), informational (1), low (2), medium (3), high (4), critical (5) }
		 MAX-ACCESS 	 accessible-for-notify
		 STATUS 	 current
		 DESCRIPTION
		   "Severity associated with the SCTP event; Values are informational, low, medium, high, critical."
		 ::= { panCommonEventObjs 702}
--
--

	 panSctpChunkType OBJECT-TYPE
		 SYNTAX 	 OCTET STRING (SIZE (1..32))
		 MAX-ACCESS 	 accessible-for-notify
		 STATUS 	 current
		 DESCRIPTION
		   "SCTP Chunk Type."
		 ::= { panCommonEventObjs 703}
--
--

	 panSctpEventType OBJECT-TYPE
		 SYNTAX 	 OCTET STRING (SIZE (1..64))
		 MAX-ACCESS 	 accessible-for-notify
		 STATUS 	 current
		 DESCRIPTION
		   "SCTP Event Type."
		 ::= { panCommonEventObjs 704}
--
--

	 panSctpEventCode OBJECT-TYPE
		 SYNTAX 	 INTEGER
		 MAX-ACCESS 	 accessible-for-notify
		 STATUS 	 current
		 DESCRIPTION
		   "SCTP Event Code"
		 ::= { panCommonEventObjs 705}
--
--

	 panSctpVerifTag1 OBJECT-TYPE
		 SYNTAX 	 Counter32
		 MAX-ACCESS 	 accessible-for-notify
		 STATUS 	 current
		 DESCRIPTION
		   "SCTP Verification Tag 1."
		 ::= { panCommonEventObjs 706}
--
--

	 panSctpVerifTag2 OBJECT-TYPE
		 SYNTAX 	 Counter32
		 MAX-ACCESS 	 accessible-for-notify
		 STATUS 	 current
		 DESCRIPTION
		   "SCTP Verification Tag 2."
		 ::= { panCommonEventObjs 707}
--
--

	 panSctpCauseCode OBJECT-TYPE
		 SYNTAX 	 OCTET STRING (SIZE (1..64))
		 MAX-ACCESS 	 accessible-for-notify
		 STATUS 	 current
		 DESCRIPTION
		   "SCTP Cause Code."
		 ::= { panCommonEventObjs 708}
--
--

	 panSctpDiamAppId OBJECT-TYPE
		 SYNTAX 	 OCTET STRING (SIZE (1..64))
		 MAX-ACCESS 	 accessible-for-notify
		 STATUS 	 current
		 DESCRIPTION
		   "Diameter Application ID."
		 ::= { panCommonEventObjs 709}
--
--

	 panSctpDiamCmdCode OBJECT-TYPE
		 SYNTAX 	 OCTET STRING (SIZE (1..64))
		 MAX-ACCESS 	 accessible-for-notify
		 STATUS 	 current
		 DESCRIPTION
		   "Diameter Command Code."
		 ::= { panCommonEventObjs 710}
--
--

	 panSctpDiamAvpCode OBJECT-TYPE
		 SYNTAX 	 Counter32
		 MAX-ACCESS 	 accessible-for-notify
		 STATUS 	 current
		 DESCRIPTION
		   "Diameter AVP Code."
		 ::= { panCommonEventObjs 711}
--
--

	 panSctpStreamId OBJECT-TYPE
		 SYNTAX 	 Counter32
		 MAX-ACCESS 	 accessible-for-notify
		 STATUS 	 current
		 DESCRIPTION
		   "SCTP Stream ID."
		 ::= { panCommonEventObjs 712}
--
--

	 panSctpOpCode OBJECT-TYPE
		 SYNTAX 	 OCTET STRING (SIZE (1..64))
		 MAX-ACCESS 	 accessible-for-notify
		 STATUS 	 current
		 DESCRIPTION
		   "Map Operaiton Code."
		 ::= { panCommonEventObjs 713}
--
--

	 panSctpCallingSSN OBJECT-TYPE
		 SYNTAX 	 OCTET STRING (SIZE (1..16))
		 MAX-ACCESS 	 accessible-for-notify
		 STATUS 	 current
		 DESCRIPTION
		   "SCCP Calling Party SSN."
		 ::= { panCommonEventObjs 714}
--
--

	 panSctpCallingGT OBJECT-TYPE
		 SYNTAX 	 OCTET STRING (SIZE (0..16))
		 MAX-ACCESS 	 accessible-for-notify
		 STATUS 	 current
		 DESCRIPTION
		   "SCCP Calling Global Title."
		 ::= { panCommonEventObjs 715}
--
--

	 panSctpEndReason OBJECT-TYPE
		 SYNTAX 	 OCTET STRING (SIZE (1..32))
		 MAX-ACCESS 	 accessible-for-notify
		 STATUS 	 current
		 DESCRIPTION
		   "SCTP Session end reason ."
		 ::= { panCommonEventObjs 716}
--
--

	 panSctpChunks OBJECT-TYPE
		 SYNTAX 	 Counter32
		 MAX-ACCESS 	 accessible-for-notify
		 STATUS 	 current
		 DESCRIPTION
		   "Number of total chunks (transmit and receive) for the SCTP session."
		 ::= { panCommonEventObjs 717}
--
--

	 panSctpPackets OBJECT-TYPE
		 SYNTAX 	 Counter32
		 MAX-ACCESS 	 accessible-for-notify
		 STATUS 	 current
		 DESCRIPTION
		   "Number of total packets (transmit and receive) for the SCTP session."
		 ::= { panCommonEventObjs 718}
--
--

	 panIpTagIp OBJECT-TYPE
		 SYNTAX 	 IpAddress
		 MAX-ACCESS 	 accessible-for-notify
		 STATUS 	 current
		 DESCRIPTION
		   "Tag Ip Address."
		 ::= { panCommonEventObjs 750}
--
--

	 panIpTagName OBJECT-TYPE
		 SYNTAX 	 OCTET STRING (SIZE (1..128))
		 MAX-ACCESS 	 accessible-for-notify
		 STATUS 	 current
		 DESCRIPTION
		   "Tag Name."
		 ::= { panCommonEventObjs 751}
--
--

	 panIpTagEvent OBJECT-TYPE
		 SYNTAX 	 OCTET STRING (SIZE (1..32))
		 MAX-ACCESS 	 accessible-for-notify
		 STATUS 	 current
		 DESCRIPTION
		   "Tag Event"
		 ::= { panCommonEventObjs 752}
--
--

	 panIpTagRepeatCount OBJECT-TYPE
		 SYNTAX 	 Counter32
		 MAX-ACCESS 	 accessible-for-notify
		 STATUS 	 current
		 DESCRIPTION
		   "Repeat of the event."
		 ::= { panCommonEventObjs 753}
--
--

	 panIpTagTimeout OBJECT-TYPE
		 SYNTAX 	 Counter32
		 MAX-ACCESS 	 accessible-for-notify
		 STATUS 	 current
		 DESCRIPTION
		   "Tag Timeout"
		 ::= { panCommonEventObjs 754}
--
--

	 panIpTagDataSourceName OBJECT-TYPE
		 SYNTAX 	 OCTET STRING (SIZE (1..64))
		 MAX-ACCESS 	 accessible-for-notify
		 STATUS 	 current
		 DESCRIPTION
		   "Tag Data Source Name"
		 ::= { panCommonEventObjs 755}
--
--

	 panIpTagDataSourceType OBJECT-TYPE
		 SYNTAX 	 OCTET STRING (SIZE (1..32))
		 MAX-ACCESS 	 accessible-for-notify
		 STATUS 	 current
		 DESCRIPTION
		   "Tag Data Source Type"
		 ::= { panCommonEventObjs 756}
--
--

	 panIpTagDataSourceSubType OBJECT-TYPE
		 SYNTAX 	 OCTET STRING (SIZE (1..32))
		 MAX-ACCESS 	 accessible-for-notify
		 STATUS 	 current
		 DESCRIPTION
		   "Tag Data Source SubType"
		 ::= { panCommonEventObjs 757}
--
--

	 panDecryptTLSVersion OBJECT-TYPE
		 SYNTAX 	 INTEGER
		 MAX-ACCESS 	 accessible-for-notify
		 STATUS 	 current
		 DESCRIPTION
		   "TLS Version."
		 ::= { panCommonEventObjs 800}
--
--

	 panDecryptTLSKeyXchg OBJECT-TYPE
		 SYNTAX 	 INTEGER
		 MAX-ACCESS 	 accessible-for-notify
		 STATUS 	 current
		 DESCRIPTION
		   "Key Exchange Algorithm."
		 ::= { panCommonEventObjs 801}
--
--

	 panDecryptTLSEnc OBJECT-TYPE
		 SYNTAX 	 INTEGER
		 MAX-ACCESS 	 accessible-for-notify
		 STATUS 	 current
		 DESCRIPTION
		   "Encryption Algorithm."
		 ::= { panCommonEventObjs 802}
--
--

	 panDecryptTLSAuth OBJECT-TYPE
		 SYNTAX 	 INTEGER
		 MAX-ACCESS 	 accessible-for-notify
		 STATUS 	 current
		 DESCRIPTION
		   "Hash Algorithm."
		 ::= { panCommonEventObjs 803}
--
--

	 panDecryptECUrve OBJECT-TYPE
		 SYNTAX 	 INTEGER
		 MAX-ACCESS 	 accessible-for-notify
		 STATUS 	 current
		 DESCRIPTION
		   "Elaptic Curve."
		 ::= { panCommonEventObjs 804}
--
--

	 panDecryptErrIndex OBJECT-TYPE
		 SYNTAX 	 INTEGER
		 MAX-ACCESS 	 accessible-for-notify
		 STATUS 	 current
		 DESCRIPTION
		   "Error Index."
		 ::= { panCommonEventObjs 805}
--
--

	 panDecryptProxyType OBJECT-TYPE
		 SYNTAX 	 INTEGER
		 MAX-ACCESS 	 accessible-for-notify
		 STATUS 	 current
		 DESCRIPTION
		   "Proxy Type."
		 ::= { panCommonEventObjs 806}
--
--

	 panDecryptCertFlags OBJECT-TYPE
		 SYNTAX 	 INTEGER
		 MAX-ACCESS 	 accessible-for-notify
		 STATUS 	 current
		 DESCRIPTION
		   "Cert Flags."
		 ::= { panCommonEventObjs 807}
--
--

	 panDecryptCN OBJECT-TYPE
		 SYNTAX 	 OCTET STRING (SIZE (1..64))
		 MAX-ACCESS 	 accessible-for-notify
		 STATUS 	 current
		 DESCRIPTION
		   "Common Name."
		 ::= { panCommonEventObjs 808}
--
--

	 panDecryptIssuerCN OBJECT-TYPE
		 SYNTAX 	 OCTET STRING (SIZE (1..64))
		 MAX-ACCESS 	 accessible-for-notify
		 STATUS 	 current
		 DESCRIPTION
		   "Issuer Common Name."
		 ::= { panCommonEventObjs 809}
--
--

	 panDecryptRootCN OBJECT-TYPE
		 SYNTAX 	 OCTET STRING (SIZE (1..64))
		 MAX-ACCESS 	 accessible-for-notify
		 STATUS 	 current
		 DESCRIPTION
		   "Root Common Name."
		 ::= { panCommonEventObjs 810}
--
--

	 panDecryptSNI OBJECT-TYPE
		 SYNTAX 	 OCTET STRING (SIZE (1..64))
		 MAX-ACCESS 	 accessible-for-notify
		 STATUS 	 current
		 DESCRIPTION
		   "Server Name Indication."
		 ::= { panCommonEventObjs 811}
--
--

	 panDecryptNotAfter OBJECT-TYPE
		 SYNTAX 	 Counter32
		 MAX-ACCESS 	 accessible-for-notify
		 STATUS 	 current
		 DESCRIPTION
		   "Not After."
		 ::= { panCommonEventObjs 812}
--
--

	 panDecryptNotBefore OBJECT-TYPE
		 SYNTAX 	 Counter32
		 MAX-ACCESS 	 accessible-for-notify
		 STATUS 	 current
		 DESCRIPTION
		   "Not Before."
		 ::= { panCommonEventObjs 813}
--
--

	 panDecryptPolicyName OBJECT-TYPE
		 SYNTAX 	 OCTET STRING (SIZE (1..64))
		 MAX-ACCESS 	 accessible-for-notify
		 STATUS 	 current
		 DESCRIPTION
		   "Policy Name."
		 ::= { panCommonEventObjs 814}
--
--

	 panDecryptCertSerial OBJECT-TYPE
		 SYNTAX 	 OCTET STRING (SIZE (1..64))
		 MAX-ACCESS 	 accessible-for-notify
		 STATUS 	 current
		 DESCRIPTION
		   "Serial No."
		 ::= { panCommonEventObjs 815}
--
--

	 panDecryptDigest OBJECT-TYPE
		 SYNTAX 	 OCTET STRING (SIZE (1..128))
		 MAX-ACCESS 	 accessible-for-notify
		 STATUS 	 current
		 DESCRIPTION
		   "FingerPrint."
		 ::= { panCommonEventObjs 816}
--
--

	 panDecryptError OBJECT-TYPE
		 SYNTAX 	 OCTET STRING (SIZE (1..512))
		 MAX-ACCESS 	 accessible-for-notify
		 STATUS 	 current
		 DESCRIPTION
		   "Error."
		 ::= { panCommonEventObjs 817}
--
--

	 panSrcDAG OBJECT-TYPE
		 SYNTAX 	 OCTET STRING (SIZE (1..256))
		 MAX-ACCESS 	 accessible-for-notify
		 STATUS 	 current
		 DESCRIPTION
		   "Source DAG."
		 ::= { panCommonEventObjs 818}
--
--

	 panDstDAG OBJECT-TYPE
		 SYNTAX 	 OCTET STRING (SIZE (1..256))
		 MAX-ACCESS 	 accessible-for-notify
		 STATUS 	 current
		 DESCRIPTION
		   "Destination DAG."
		 ::= { panCommonEventObjs 819}
--
--

	 panSrcEDL OBJECT-TYPE
		 SYNTAX 	 OCTET STRING (SIZE (1..64))
		 MAX-ACCESS 	 accessible-for-notify
		 STATUS 	 current
		 DESCRIPTION
		   "Source EDL."
		 ::= { panCommonEventObjs 820}
--
--

	 panDstEDL OBJECT-TYPE
		 SYNTAX 	 OCTET STRING (SIZE (1..64))
		 MAX-ACCESS 	 accessible-for-notify
		 STATUS 	 current
		 DESCRIPTION
		   "Destination EDL."
		 ::= { panCommonEventObjs 821}
--
--

	 panDomainEDL OBJECT-TYPE
		 SYNTAX 	 OCTET STRING (SIZE (1..64))
		 MAX-ACCESS 	 accessible-for-notify
		 STATUS 	 current
		 DESCRIPTION
		   "Destination EDL."
		 ::= { panCommonEventObjs 822}
--
--

	 panGlobalProtectStatus OBJECT-TYPE
		 SYNTAX 	 INTEGER
		 MAX-ACCESS 	 accessible-for-notify
		 STATUS 	 current
		 DESCRIPTION
		   "Status."
		 ::= { panCommonEventObjs 900}
--
--

	 panGlobalProtectStage OBJECT-TYPE
		 SYNTAX 	 OCTET STRING (SIZE (1..16))
		 MAX-ACCESS 	 accessible-for-notify
		 STATUS 	 current
		 DESCRIPTION
		   "Stage."
		 ::= { panCommonEventObjs 901}
--
--

	 panGlobalProtectAuthMethod OBJECT-TYPE
		 SYNTAX 	 OCTET STRING (SIZE (1..16))
		 MAX-ACCESS 	 accessible-for-notify
		 STATUS 	 current
		 DESCRIPTION
		   "Authentication Method."
		 ::= { panCommonEventObjs 902}
--
--

	 panGlobalProtectTunnelType OBJECT-TYPE
		 SYNTAX 	 OCTET STRING (SIZE (1..16))
		 MAX-ACCESS 	 accessible-for-notify
		 STATUS 	 current
		 DESCRIPTION
		   "Tunnel Type."
		 ::= { panCommonEventObjs 903}
--
--

	 panGlobalProtectPortal OBJECT-TYPE
		 SYNTAX 	 OCTET STRING (SIZE (1..32))
		 MAX-ACCESS 	 accessible-for-notify
		 STATUS 	 current
		 DESCRIPTION
		   "Portal."
		 ::= { panCommonEventObjs 904}
--
--

	 panGlobalProtectSrcRegion OBJECT-TYPE
		 SYNTAX 	 OCTET STRING (SIZE (1..32))
		 MAX-ACCESS 	 accessible-for-notify
		 STATUS 	 current
		 DESCRIPTION
		   "Source Region."
		 ::= { panCommonEventObjs 905}
--
--

	 panGlobalProtectPublicIP OBJECT-TYPE
		 SYNTAX 	 IpAddress
		 MAX-ACCESS 	 accessible-for-notify
		 STATUS 	 current
		 DESCRIPTION
		   "Public IP."
		 ::= { panCommonEventObjs 906}
--
--

	 panGlobalProtectPublicIPv6 OBJECT-TYPE
		 SYNTAX 	 IpAddress
		 MAX-ACCESS 	 accessible-for-notify
		 STATUS 	 current
		 DESCRIPTION
		   "Public IPv6."
		 ::= { panCommonEventObjs 907}
--
--

	 panGlobalProtectPrivateIP OBJECT-TYPE
		 SYNTAX 	 IpAddress
		 MAX-ACCESS 	 accessible-for-notify
		 STATUS 	 current
		 DESCRIPTION
		   "Private IP."
		 ::= { panCommonEventObjs 908}
--
--

	 panGlobalProtectPrivateIPv6 OBJECT-TYPE
		 SYNTAX 	 IpAddress
		 MAX-ACCESS 	 accessible-for-notify
		 STATUS 	 current
		 DESCRIPTION
		   "Private IPv6."
		 ::= { panCommonEventObjs 909}
--
--

	 panGlobalProtectClientVersion OBJECT-TYPE
		 SYNTAX 	 INTEGER
		 MAX-ACCESS 	 accessible-for-notify
		 STATUS 	 current
		 DESCRIPTION
		   "Client Version."
		 ::= { panCommonEventObjs 910}
--
--

	 panGlobalProtectClientOSVersion OBJECT-TYPE
		 SYNTAX 	 OCTET STRING (SIZE (1..64))
		 MAX-ACCESS 	 accessible-for-notify
		 STATUS 	 current
		 DESCRIPTION
		   "Client OS Version."
		 ::= { panCommonEventObjs 911}
--
--

	 panGlobalProtectLoginDuration OBJECT-TYPE
		 SYNTAX 	 INTEGER
		 MAX-ACCESS 	 accessible-for-notify
		 STATUS 	 current
		 DESCRIPTION
		   "Login Duration."
		 ::= { panCommonEventObjs 912}
--
--

	 panGlobalProtectConnectMethod OBJECT-TYPE
		 SYNTAX 	 OCTET STRING (SIZE (1..32))
		 MAX-ACCESS 	 accessible-for-notify
		 STATUS 	 current
		 DESCRIPTION
		   "Connect Method."
		 ::= { panCommonEventObjs 913}
--
--

	 panGlobalProtectReason OBJECT-TYPE
		 SYNTAX 	 OCTET STRING (SIZE (1..32))
		 MAX-ACCESS 	 accessible-for-notify
		 STATUS 	 current
		 DESCRIPTION
		   "Reason."
		 ::= { panCommonEventObjs 914}
--
--

	 panGlobalProtectLocation OBJECT-TYPE
		 SYNTAX 	 OCTET STRING (SIZE (1..128))
		 MAX-ACCESS 	 accessible-for-notify
		 STATUS 	 current
		 DESCRIPTION
		   "Location."
		 ::= { panCommonEventObjs 915}
--
--

	 panGlobalProtectErrorCode OBJECT-TYPE
		 SYNTAX 	 INTEGER
		 MAX-ACCESS 	 accessible-for-notify
		 STATUS 	 current
		 DESCRIPTION
		   "Error Code."
		 ::= { panCommonEventObjs 916}
--
--

	 panGlobalProtectError OBJECT-TYPE
		 SYNTAX 	 OCTET STRING (SIZE (1..64))
		 MAX-ACCESS 	 accessible-for-notify
		 STATUS 	 current
		 DESCRIPTION
		   "Error."
		 ::= { panCommonEventObjs 917}
--
--

	 panGlobalProtectSelectionType OBJECT-TYPE
		 SYNTAX 	 OCTET STRING (SIZE (1..16))
		 MAX-ACCESS 	 accessible-for-notify
		 STATUS 	 current
		 DESCRIPTION
		   "Selection Type."
		 ::= { panCommonEventObjs 918}
--
--

	 panGlobalProtectResponseTime OBJECT-TYPE
		 SYNTAX 	 INTEGER
		 MAX-ACCESS 	 accessible-for-notify
		 STATUS 	 current
		 DESCRIPTION
		   "Response Time"
		 ::= { panCommonEventObjs 919}
--
--

	 panGlobalProtectPriority OBJECT-TYPE
		 SYNTAX 	 INTEGER
		 MAX-ACCESS 	 accessible-for-notify
		 STATUS 	 current
		 DESCRIPTION
		   "Priority"
		 ::= { panCommonEventObjs 920}
--
--

	 panGlobalProtectAttemptedGateways OBJECT-TYPE
		 SYNTAX 	 OCTET STRING (SIZE (1..512))
		 MAX-ACCESS 	 accessible-for-notify
		 STATUS 	 current
		 DESCRIPTION
		   "Attempted Gateways"
		 ::= { panCommonEventObjs 921}
--
--

	 panGlobalProtectHostId OBJECT-TYPE
		 SYNTAX 	 OCTET STRING (SIZE (1..128))
		 MAX-ACCESS 	 accessible-for-notify
		 STATUS 	 current
		 DESCRIPTION
		   "Host ID"
		 ::= { panCommonEventObjs 922}
--
--

	 panGlobalProtectSerialNo OBJECT-TYPE
		 SYNTAX 	 OCTET STRING (SIZE (1..128))
		 MAX-ACCESS 	 accessible-for-notify
		 STATUS 	 current
		 DESCRIPTION
		   ""
		 ::= { panCommonEventObjs 923}
----------------------------------------------------------------------------
-- TRAPS: CONFIG TRAFFIC THREAT HIPMATCH
----------------------------------------------------------------------------

	 panConfigTrap NOTIFICATION-TYPE
	   OBJECTS {
		 panReceiveTime, panSerial, panEventType, panEventSubType, panHost, panVsys, panSeqno, panActionflags, panHostname, panConfigCmd, panConfigAdmin, panConfigClient, panConfigResult, panConfigPath
		 }
	 STATUS 	 current
	 DESCRIPTION
	   "A configuratioon event trap."
	 ::={panCommonEventEventsV2 2}

	 panTrafficTrap NOTIFICATION-TYPE
	   OBJECTS {
		 panReceiveTime, panSerial, panEventType, panEventSubType, panVsys, panSeqno, panActionflags, panHostname, panSource, panDestination, panNatSource, panNatDestination, panRule, panSrcUser, panDstUser, panApplication, panSourceZone, panDestinationZone, panIngressInterface, panEgressInterface, panLogForwardingProfile, panSessionID, panRepeatCount, panSourcePort, panDestinationPort, panNatSourcePort, panNatDestinationPort, panFlags, panProtocol, panAction, panTimeGenerated, panSrcloc, panDstloc, panXffInetAddrType, panXffInetAddr, panSourceUUID, panDestinationUUID, panRuleUUID, panTunnel, panTrafficBytes, panTrafficPackets, panTrafficStartTime, panTrafficElapsed, panTrafficCategory, panTrafficSessionEndReason, panTrafficTunnelID, panTrafficImsi, panTrafficMonitorTag, panTrafficImei, panTrafficParentSessionId, panTrafficParentStartTime, panTrafficSrcDevCat, panTrafficDstDevCat, panTrafficSrcDevPro, panTrafficDstDevPro, panTrafficSrcDevMod, panTrafficDstDevMod, panTrafficSrcDevVen, panTrafficDstDevVen, panTrafficSrcOSFam, panTrafficDstOSFam, panTrafficSrcOSVer, panTrafficDstOSVer, panTrafficSrcHost, panTrafficDstHost, panTrafficSrcMAC, panTrafficDstMAC, panContainerId, panPodNamespace, panPodName, panHostId, panSerialNo
		 }
	 STATUS 	 current
	 DESCRIPTION
	   "A traffic event trap."
	 ::={panCommonEventEventsV2 3}

	 panThreatTrap NOTIFICATION-TYPE
	   OBJECTS {
		 panReceiveTime, panSerial, panEventType, panEventSubType, panVsys, panSeqno, panActionflags, panHostname, panSource, panDestination, panNatSource, panNatDestination, panRule, panSrcUser, panDstUser, panApplication, panSourceZone, panDestinationZone, panIngressInterface, panEgressInterface, panLogForwardingProfile, panSessionID, panRepeatCount, panSourcePort, panDestinationPort, panNatSourcePort, panNatDestinationPort, panFlags, panProtocol, panAction, panTimeGenerated, panXffInetAddrType, panXffInetAddr, panSrcloc, panDstloc, panSourceUUID, panDestinationUUID, panRuleUUID, panTunnel, panThreatId, panThreatCategory, panThreatContentType, panThreatSeverity, panThreatDirection, panMiscellaneous, panPcapId, panFileDigest, panCloud, panUrlIndex, panUserAgent, panXff, panReferer, panSender, panSubject, panRecipient, panFileType, panReportId, panHttpMethod, panThreatTunnelID, panThreatImsi, panThreatMonitorTag, panThreatImei, panThreatParentSessionId, panThreatParentStartTime, panThrCategory, panThreatSrcDevCat, panThreatDstDevCat, panThreatSrcDevPro, panThreatDstDevPro, panThreatSrcDevMod, panThreatDstDevMod, panThreatSrcDevVen, panThreatDstDevVen, panThreatSrcOSFam, panThreatDstOSFam, panThreatSrcOSVer, panThreatDstOSVer, panThreatSrcHost, panThreatDstHost, panThreatSrcMAC, panThreatDstMAC, panContainerId, panPodNamespace, panPodName, panHostId, panSerialNo
		 }
	 STATUS 	 current
	 DESCRIPTION
	   "A threat/URL event trap."
	 ::={panCommonEventEventsV2 4}

	 panHipMatchTrap NOTIFICATION-TYPE
	   OBJECTS {
		 panReceiveTime, panSerial, panEventType, panEventSubType, panVsys, panSeqno, panActionflags, panHostname, panHipSourceUser, panHipMachineName, panHipMatch, panHipMatchType, panHipRepeatCount, panHipOS, panHipSourceIPv6, panHipMAC
		 }
	 STATUS 	 current
	 DESCRIPTION
	   "A Hipmatch event trap."
	 ::={panCommonEventEventsV2 5}

	 panGtpTrap NOTIFICATION-TYPE
	   OBJECTS {
		 panReceiveTime, panSerial, panEventType, panEventSubType, panVsys, panSeqno, panActionflags, panHostname, panSource, panDestination, panNatSource, panNatDestination, panRule, panSrcUser, panDstUser, panApplication, panSourceZone, panDestinationZone, panIngressInterface, panEgressInterface, panLogForwardingProfile, panSessionID, panRepeatCount, panSourcePort, panDestinationPort, panNatSourcePort, panNatDestinationPort, panFlags, panProtocol, panAction, panTimeGenerated, panSrcloc, panDstloc, panXffInetAddrType, panXffInetAddr, panTunnel, panGtpParentSessionId, panGtpParentStartTime, panGtpMsisdn, panGtpApn, panGtpRat, panGtpMsgType, panGtpTunnelID, panGtpImsi, panGtpMonitorTag, panGtpImei, panGtpInterface, panGtpCauseCode, panGtpEventType, panGtpSeverity, panGtpMcc, panGtpMnc, panGtpEventCode, panGtpBytes, panGtpPackets, panGtpMaxEncap, panGtpUnknownProto, panGtpStrictCheck, panGtpTunnelFragment, panGtpSessionsCreated, panGtpSessionsClosed, panGtpSessionEndReason, panGtpActionSource, panGtpStartTime, panGtpElapsed, panGtpTCIRule, panGtpRemoteUserIp, panGtpRemoteUserId, panRuleUUID, panContainerId, panPodNamespace, panPodName
		 }
	 STATUS 	 current
	 DESCRIPTION
	   "A Tunnel/GTP event trap."
	 ::={panCommonEventEventsV2 6}

	 panUseridTrap NOTIFICATION-TYPE
	   OBJECTS {
		 panReceiveTime, panSerial, panEventType, panEventSubType, panVsys, panSeqno, panActionflags, panHostname, panUseridSourceInetAddrType,panUseridSourceInetAddr, panUseridUser, panUseridDataSourceName, panUseridEventID, panUseridRepeatCount, panUseridTimeout, panUseridBeginport, panUseridEndport, panUseridDataSource, panUseridDataSourceType, panUseridFactorType, panUseridFactorTime, panUseridFactorNo
		 }
	 STATUS 	 current
	 DESCRIPTION
	   "A Userid event trap."
	 ::={panCommonEventEventsV2 7}

	 panAuthTrap NOTIFICATION-TYPE
	   OBJECTS {
		 panReceiveTime, panSerial, panEventType, panEventSubType, panVsys, panSeqno, panActionflags, panHostname, panUseridSourceInetAddrType,panUseridSourceInetAddr, panAuthUser, panAuthNormalizeUser, panAuthObject, panAuthPolicy, panAuthRepeatCount, panAuthID, panAuthVendor, panAuthLogForwardingProfile, panAuthClientType, panAuthDescription, panAuthServerProfile, panAuthEvent, panAuthFactorNo, panAuthProto
		 }
	 STATUS 	 current
	 DESCRIPTION
	   "A Authentication event trap."
	 ::={panCommonEventEventsV2 8}

	 panSctpTrap NOTIFICATION-TYPE
	   OBJECTS {
		 panReceiveTime, panSerial, panEventType, panEventSubType, panVsys, panSeqno, panActionflags, panSource, panDestination, panNatSource, panNatDestination, panRule, panSrcUser, panDstUser, panApplication, panSourceZone, panDestinationZone, panIngressInterface, panEgressInterface, panLogForwardingProfile, panSessionID, panRepeatCount, panSourcePort, panDestinationPort, panNatSourcePort, panNatDestinationPort, panFlags, panProtocol, panAction, panTimeGenerated, panSrcloc, panDstloc, panXffInetAddrType, panXffInetAddr, panSourceInetAddrType, panSourceInetAddr, panSctpAssocId, panSctpPpid, panSctpSeverity, panSctpChunkType, panSctpEventType, panSctpEventCode, panSctpVerifTag1, panSctpVerifTag2, panSctpCauseCode, panSctpDiamAppId, panSctpDiamCmdCode, panSctpDiamAvpCode, panSctpStreamId, panSctpOpCode, panSctpCallingSSN, panSctpCallingGT, panSctpEndReason, panSctpChunks, panSctpPackets, panRuleUUID, panContainerId, panPodNamespace, panPodName
		 }
	 STATUS 	 current
	 DESCRIPTION
	   "A SCTP event trap."
	 ::={panCommonEventEventsV2 9}

	 panCorrTrap NOTIFICATION-TYPE
	   OBJECTS {
		 panReceiveTime, panSerial, panEventType, panVsys, panCorrSeverity, panCorrDG1, panCorrDG2, panCorrDG3, panCorrDG4, panHostname, panCorrObjName, panCorrObjID, panCorrEvidence, panHostId, panSerialNo
		 }
	 STATUS 	 current
	 DESCRIPTION
	   "A Correlation event trap."
	 ::={panCommonEventEventsV2 10}

	 panIpTagTrap NOTIFICATION-TYPE
	   OBJECTS {
		 panReceiveTime, panSerial, panEventType, panEventSubType, panVsys, panSeqno, panActionflags, panHostname, panIpTagIp, panIpTagName, panIpTagEvent, panIpTagRepeatCount, panIpTagTimeout, panIpTagDataSourceName, panIpTagDataSourceType, panIpTagDataSourceSubType
		 }
	 STATUS 	 current
	 DESCRIPTION
	   "A IP-Tag event trap."
	 ::={panCommonEventEventsV2 11}

	 panDecryptionTrap NOTIFICATION-TYPE
	   OBJECTS {
		 panReceiveTime, panSerial, panEventType, panEventSubType, panVsys, panSeqno, panActionflags, panHostname, panSource, panDestination, panNatSource, panNatDestination, panRule, panSrcUser, panDstUser, panApplication, panSourceZone, panDestinationZone, panIngressInterface, panEgressInterface, panLogForwardingProfile, panSessionID, panRepeatCount, panSourcePort, panDestinationPort, panNatSourcePort, panNatDestinationPort, panFlags, panProtocol, panAction, panTimeGenerated, panSrcloc, panDstloc, panRuleUUID, panDecryptTLSVersion, panDecryptTLSKeyXchg, panDecryptTLSEnc, panDecryptTLSAuth, panDecryptECUrve, panDecryptErrIndex, panDecryptProxyType, panDecryptCN, panDecryptCertFlags, panDecryptNotBefore, panDecryptSNI, panDecryptNotAfter, panDecryptPolicyName, panDecryptRootCN, panDecryptIssuerCN, panDecryptCertSerial, panDecryptDigest, panContainerId, panPodNamespace, panPodName, panSrcDAG, panDstDAG
		 }
	 STATUS 	 current
	 DESCRIPTION
	   "A decryption event trap."
	 ::={panCommonEventEventsV2 12}

	 panGlobalprotectTrap NOTIFICATION-TYPE
	   OBJECTS {
		 panReceiveTime, panSerial, panEventType, panEventSubType, panVsys, panSeqno, panActionflags, panHostname, panSystemEventId, panGlobalProtectStatus, panGlobalProtectStage, panGlobalProtectAuthMethod, panGlobalProtectTunnelType, panGlobalProtectPortal, panSrcUser, panGlobalProtectSrcRegion, panHipMachineName, panGlobalProtectPublicIP, panGlobalProtectPublicIPv6, panGlobalProtectPrivateIP, panGlobalProtectPrivateIPv6, panGlobalProtectHostId, panGlobalProtectSerialNo, panGlobalProtectClientVersion, panGlobalProtectClientOSVersion, panLogForwardingProfile, panRepeatCount, panGlobalProtectLoginDuration, panGlobalProtectConnectMethod, panGlobalProtectReason, panGlobalProtectLocation, panGlobalProtectErrorCode, panGlobalProtectError, panSystemDescription, panGlobalProtectSelectionType, panGlobalProtectResponseTime, panGlobalProtectPriority, panGlobalProtectAttemptedGateways
		 }
	 STATUS 	 current
	 DESCRIPTION
	   "A Globalprotect event trap."
	 ::={panCommonEventEventsV2 13}
----------------------------------------------------------------------------
-- TRAPS: SYSTEM LOG EVENTS
----------------------------------------------------------------------------

	 panCryptoCertExpiryTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Certificate expired"
	 ::={panCommonEventEventsV2 100}

	 panCryptoMkeyExpiryTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Master key expired"
	 ::={panCommonEventEventsV2 101}

	 panCryptoMkeyExpiryReminderTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Master key expiry reminder"
	 ::={panCommonEventEventsV2 102}

	 panCryptoHSMStateChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HSM state goes up/down"
	 ::={panCommonEventEventsV2 103}

	 panCryptoPrivateKeyExportTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Private key exported"
	 ::={panCommonEventEventsV2 104}

	 panCryptoDeployMkeyChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Deployed master key change"
	 ::={panCommonEventEventsV2 105}

	 panCryptoMkeyChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Master key changed"
	 ::={panCommonEventEventsV2 106}

	 panDHCPLeaseStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP lease started"
	 ::={panCommonEventEventsV2 200}

	 panDHCPLeaseEndTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP lease ended"
	 ::={panCommonEventEventsV2 201}

	 panDHCPServerOnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP server on"
	 ::={panCommonEventEventsV2 202}

	 panDHCPServerAutoProbeOnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP server auto-probe finished turn on DHCP server since no offer received"
	 ::={panCommonEventEventsV2 203}

	 panDHCPServerAutoProbeOffTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP server auto-probe finished turn off DHCP server since received offer"
	 ::={panCommonEventEventsV2 204}

	 panDHCPServerNoFreeIpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP server runs out of ip pool"
	 ::={panCommonEventEventsV2 205}

	 panDHCPIpAlreadyInUseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ip address is already in use"
	 ::={panCommonEventEventsV2 206}

	 panDHCPRelayOnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP relay on"
	 ::={panCommonEventEventsV2 207}

	 panDHCPRelayOffTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP relay off"
	 ::={panCommonEventEventsV2 208}

	 panDHCPRelay6OnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPv6 relay on"
	 ::={panCommonEventEventsV2 209}

	 panDHCPRelay6OffTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPv6 relay off"
	 ::={panCommonEventEventsV2 210}

	 panDHCPIfUpdateFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface update fail"
	 ::={panCommonEventEventsV2 211}

	 panDHCPIfUpdateOkTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface update successful"
	 ::={panCommonEventEventsV2 212}

	 panDHCPIfClearTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface info cleared"
	 ::={panCommonEventEventsV2 213}

	 panDHCPIfRenewTriggerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface renew triggered"
	 ::={panCommonEventEventsV2 214}

	 panDHCPIfReleaseTriggerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface release triggered"
	 ::={panCommonEventEventsV2 215}

	 panDHCPIfRcvNakTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface received nak"
	 ::={panCommonEventEventsV2 216}

	 panDHCPIfInheritTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP server interface inherited settings"
	 ::={panCommonEventEventsV2 217}

	 panDHCPIfDuplicateIpIntfTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface received IP address already assigned to another interface"
	 ::={panCommonEventEventsV2 218}

	 panDHCPIfDuplicateIpRemoteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCP client interface received IP address already used by another host on the network"
	 ::={panCommonEventEventsV2 219}

	 panDHCPV6IfUpdateFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 update fail"
	 ::={panCommonEventEventsV2 220}

	 panDHCPV6IfUpdateOkTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 update successful"
	 ::={panCommonEventEventsV2 221}

	 panDHCPV6IfClearTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 info cleared"
	 ::={panCommonEventEventsV2 222}

	 panDHCPV6IfRenewTriggerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 renew triggered"
	 ::={panCommonEventEventsV2 223}

	 panDHCPV6IfReleaseTriggerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 release triggered"
	 ::={panCommonEventEventsV2 224}

	 panDHCPV6IfConfirmFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 confirm failed,continuing with the existing addresses"
	 ::={panCommonEventEventsV2 225}

	 panDHCPV6IfDuplicateIpIntfTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 received IP address already assigned to another interface"
	 ::={panCommonEventEventsV2 226}

	 panDHCPV6IfDuplicateIpRemoteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 received IP address already used by another host on the network"
	 ::={panCommonEventEventsV2 227}

	 panDHCPV6IfIanaNotReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 unable to obtain Non-temporary address from the Server"
	 ::={panCommonEventEventsV2 228}

	 panDHCPV6IfIataNotReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 unable to obtain Temporary address from the Server"
	 ::={panCommonEventEventsV2 229}

	 panDHCPV6IfIapdNotReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 unable to obtain Prefix Delegation address from the Server"
	 ::={panCommonEventEventsV2 230}

	 panDHCPV6IfDhcpv6LeaseStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 lease of addresses started"
	 ::={panCommonEventEventsV2 231}

	 panDHCPV6IfDhcpv6PreferredLifetimeOverTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Preferred lifetime of addresses expired"
	 ::={panCommonEventEventsV2 232}

	 panDHCPV6IfDhcpv6LeaseEndTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Lease of addresses"
	 ::={panCommonEventEventsV2 233}

	 panDHCPV6IfDuplicateAddressReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 IPv6 address ip_address on interface if_name failed due to duplicate IP check"
	 ::={panCommonEventEventsV2 234}

	 panDHCPV6IfPdIdentifierValueTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Prefix cannot be assigned to the Inherited Interface if_name,since the value of the Pool identifier is larger the prefix range received."
	 ::={panCommonEventEventsV2 235}

	 panDHCPV6IfPdExhaustTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Prefix cannot be assigned to the Inherited Interface,since the prefix pool exhausted."
	 ::={panCommonEventEventsV2 236}

	 panDNSProxyCacheClearedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DNS Proxy cache cleared"
	 ::={panCommonEventEventsV2 300}

	 panDNSProxyResolveFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to resolve domain name"
	 ::={panCommonEventEventsV2 301}

	 panDNSProxyObjectEnableTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Enabled/Disabled DNS proxy object"
	 ::={panCommonEventEventsV2 302}

	 panDNSProxyIfAddTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Assigned interface to DNS proxy object"
	 ::={panCommonEventEventsV2 303}

	 panDNSProxyIfDelTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Removed interface from DNS proxy object"
	 ::={panCommonEventEventsV2 304}

	 panDNSProxyIfInheritTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DNS Proxy object inherited settings"
	 ::={panCommonEventEventsV2 305}

	 panDOSDosRuleChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DOS rule changed"
	 ::={panCommonEventEventsV2 500}

	 panGeneralGeneralTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "General system event"
	 ::={panCommonEventEventsV2 600}

	 panGeneralSystemStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "System start"
	 ::={panCommonEventEventsV2 601}

	 panGeneralSystemShutdownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "System shutdown"
	 ::={panCommonEventEventsV2 602}

	 panGeneralAuthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Authentication attempt faliure"
	 ::={panCommonEventEventsV2 603}

	 panGeneralAuthSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Authentication attempt success"
	 ::={panCommonEventEventsV2 604}

	 panGeneralTacLoginTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TAC debug access attempt"
	 ::={panCommonEventEventsV2 605}

	 panGeneralAuthServerDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not contact auth server"
	 ::={panCommonEventEventsV2 606}

	 panGeneralAdminDiscardTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Discarded by administrator"
	 ::={panCommonEventEventsV2 607}

	 panGeneralBootstrapFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Bootstrap vm failed authentication with panorama"
	 ::={panCommonEventEventsV2 608}

	 panGeneralWfRealtimeEnabledTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire Real-time feature enabled"
	 ::={panCommonEventEventsV2 609}

	 panGeneralWfRealtimeDisabledTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire Real-time feature disabled"
	 ::={panCommonEventEventsV2 610}

	 panGeneralInodeUsageLimitExceededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Inode Usage Exceeded"
	 ::={panCommonEventEventsV2 611}

	 panGlobalprotectgatewayRegistSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway user login succeeded."
	 ::={panCommonEventEventsV2 700}

	 panGlobalprotectgatewayRegistFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway user login failed."
	 ::={panCommonEventEventsV2 701}

	 panGlobalprotectgatewayLogoutSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway user logout succeeded."
	 ::={panCommonEventEventsV2 702}

	 panGlobalprotectgatewayLogoutFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway user logout failed."
	 ::={panCommonEventEventsV2 703}

	 panGlobalProtectGatewayConfigSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway client configuration generated."
	 ::={panCommonEventEventsV2 704}

	 panGlobalProtectGatewayConfigFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway client configuration failed."
	 ::={panCommonEventEventsV2 705}

	 panGlobalProtectGatewayConfigReleaseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway client configuration released."
	 ::={panCommonEventEventsV2 706}

	 panGlobalProtectGatewaySwitchSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway client switch to SSL tunnel mode succeeded."
	 ::={panCommonEventEventsV2 707}

	 panGlobalProtectGatewaySwitchFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway client switch to SSL tunnel mode failed."
	 ::={panCommonEventEventsV2 708}

	 panGlobalProtectGatewayAuthSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway user authentication succeeded."
	 ::={panCommonEventEventsV2 709}

	 panGlobalProtectGatewayAuthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway user authentication failed."
	 ::={panCommonEventEventsV2 710}

	 panGlobalProtectGatewayAgentMsgTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway agent message."
	 ::={panCommonEventEventsV2 711}

	 panGlobalProtectGatewayInvalidLicenseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway invalid gateway license."
	 ::={panCommonEventEventsV2 712}

	 panGlobalProtectGatewayInheritanceTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway inheritance."
	 ::={panCommonEventEventsV2 713}

	 panGlobalProtectPortalConfigSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal client configuration generated."
	 ::={panCommonEventEventsV2 714}

	 panGlobalProtectPortalConfigFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal client configuration failed."
	 ::={panCommonEventEventsV2 715}

	 panGlobalProtectPortalAuthSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal user authentication succeeded."
	 ::={panCommonEventEventsV2 716}

	 panGlobalProtectPortalAuthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal user authentication failed."
	 ::={panCommonEventEventsV2 717}

	 panGlobalprotectgatewaySatauthSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway satellite authentication succeeded."
	 ::={panCommonEventEventsV2 718}

	 panGlobalprotectgatewaySatauthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway satellite authentication failed."
	 ::={panCommonEventEventsV2 719}

	 panGlobalprotectgatewayRouteAddFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway route add failure."
	 ::={panCommonEventEventsV2 720}

	 panGlobalprotectgatewayRouteResetFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway route reset failure."
	 ::={panCommonEventEventsV2 721}

	 panGlobalprotectgatewayTunUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway tunnel is up."
	 ::={panCommonEventEventsV2 722}

	 panGlobalprotectgatewayTunDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway tunnel is down."
	 ::={panCommonEventEventsV2 723}

	 panGlobalprotectgatewayDupSubnetsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway detected duplicate Satellite subnets."
	 ::={panCommonEventEventsV2 724}

	 panGlobalprotectgatewayDeniedRoutesTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway denied Satellite routes."
	 ::={panCommonEventEventsV2 725}

	 panGlobalprotectgatewayTunMonDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway tunnel monitor down."
	 ::={panCommonEventEventsV2 726}

	 panGlobalprotectgatewayTunMonUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway tunnel monitor up."
	 ::={panCommonEventEventsV2 727}

	 panGlobalprotectportalSatconfigSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal satellite configuration generated."
	 ::={panCommonEventEventsV2 728}

	 panGlobalprotectportalSatconfigFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal satellite configuration failed."
	 ::={panCommonEventEventsV2 729}

	 panGlobalprotectportalSatauthSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal satellite authentication succeeded."
	 ::={panCommonEventEventsV2 730}

	 panGlobalprotectportalSatauthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal satellite authentication failed."
	 ::={panCommonEventEventsV2 731}

	 panGlobalprotectportalSatcertSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal satellite certificate success."
	 ::={panCommonEventEventsV2 732}

	 panGlobalprotectportalSatcertFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal satellite certificate failed."
	 ::={panCommonEventEventsV2 733}

	 panGlobalprotectgatewayTunHardlifetimeExpiredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway tunnel lifetime expired."
	 ::={panCommonEventEventsV2 734}

	 panGlobalprotectgatewayTunDpInstallErrTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Site to Site Gateway tunnel dataplane install error."
	 ::={panCommonEventEventsV2 735}

	 panGlobalprotectportalGenportalcookieSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal generate portal cookie success."
	 ::={panCommonEventEventsV2 736}

	 panGlobalprotectportalGenportalcookieFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal generate portal cookie failed."
	 ::={panCommonEventEventsV2 737}

	 panGlobalprotectgatewayFramedIpSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Framed IP retrieval success"
	 ::={panCommonEventEventsV2 738}

	 panGlobalprotectgatewayFramedIpFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Framed IP retrieval failed."
	 ::={panCommonEventEventsV2 739}

	 panGlobalprotectgatewayGencookieSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway generate cookie success."
	 ::={panCommonEventEventsV2 740}

	 panGlobalprotectgatewayGencookieFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect gateway generate cookie failed."
	 ::={panCommonEventEventsV2 741}

	 panGlobalprotectgatewayFramedIpv6SuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Framed IPv6 retrieval success."
	 ::={panCommonEventEventsV2 742}

	 panGlobalprotectgatewayFramedIpv6FailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Framed IPv6 retrieval failed."
	 ::={panCommonEventEventsV2 743}

	 panGlobalprotectportalLogoutSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal user logout succeeded."
	 ::={panCommonEventEventsV2 744}

	 panGlobalprotectportalLogoutFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal user logout failed."
	 ::={panCommonEventEventsV2 745}

	 panGlobalprotectportalSetSatelliteCookieExpirationSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal set satellite cookie expiration success."
	 ::={panCommonEventEventsV2 746}

	 panGlobalprotectportalSetSatelliteCookieExpirationFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal set satellite cookie expiration failed."
	 ::={panCommonEventEventsV2 747}

	 panHAPreemptTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA device going passive due to preemption"
	 ::={panCommonEventEventsV2 800}

	 panHAStateChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA device has changed states"
	 ::={panCommonEventEventsV2 801}

	 panHAStateOverrideTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA device state override change"
	 ::={panCommonEventEventsV2 802}

	 panHADataplaneDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA has detected a dataplane down"
	 ::={panCommonEventEventsV2 803}

	 panHAPolicyPushFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA policy push to dataplane failed"
	 ::={panCommonEventEventsV2 804}

	 panHAHa1LinkChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA1 peer link change"
	 ::={panCommonEventEventsV2 805}

	 panHAHa2LinkChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA2 peer link change"
	 ::={panCommonEventEventsV2 806}

	 panHAConnectChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer connection change"
	 ::={panCommonEventEventsV2 807}

	 panHAPathMonitorDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA monitored path down"
	 ::={panCommonEventEventsV2 808}

	 panHALinkMonitorDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA monitored link down"
	 ::={panCommonEventEventsV2 809}

	 panHAHa3LinkChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA3 peer link change"
	 ::={panCommonEventEventsV2 810}

	 panHAPathMonitorUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA monitored path up"
	 ::={panCommonEventEventsV2 811}

	 panHALinkMonitorUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA monitored link up"
	 ::={panCommonEventEventsV2 812}

	 panHAHa4LinkChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA4 peer link change"
	 ::={panCommonEventEventsV2 813}

	 panHAPeerSyncFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA can't synch non-configuration controlplane data to peer"
	 ::={panCommonEventEventsV2 814}

	 panHAConfigFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA configuration push to peer has failed"
	 ::={panCommonEventEventsV2 815}

	 panHAConfigNotSynchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA config not automatically synched"
	 ::={panCommonEventEventsV2 816}

	 panHAPeerErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA error message from peer"
	 ::={panCommonEventEventsV2 817}

	 panHAPre13Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer is running pre-1.3 software"
	 ::={panCommonEventEventsV2 818}

	 panHAPre20Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer is running pre-2.0 software"
	 ::={panCommonEventEventsV2 819}

	 panHAPeerVersionMatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer other software version matching"
	 ::={panCommonEventEventsV2 820}

	 panHAPeerVersionSupportedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer version is supported with our local version"
	 ::={panCommonEventEventsV2 821}

	 panHAPeerVersionUnsupportedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer version is not supported with our local version"
	 ::={panCommonEventEventsV2 822}

	 panHAPeerVersionDegradedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer version is degraded in our local version"
	 ::={panCommonEventEventsV2 823}

	 panHAPeerCompatMismatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer compatibility mismatch"
	 ::={panCommonEventEventsV2 824}

	 panHAPeerCompatMatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer compatibility now matches"
	 ::={panCommonEventEventsV2 825}

	 panHAPeerCompatFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer compatibility failure"
	 ::={panCommonEventEventsV2 826}

	 panHAPeerSplitBrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer detected split-brain"
	 ::={panCommonEventEventsV2 827}

	 panHASplitBrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA device detected split-brain"
	 ::={panCommonEventEventsV2 828}

	 panHAPreemptLoopTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA device going suspend due to preemption-loop"
	 ::={panCommonEventEventsV2 829}

	 panHANonFunctionalLoopTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA device going suspend due to non-functional-loop"
	 ::={panCommonEventEventsV2 830}

	 panHAPeerShutdownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA peer change caused a local shutdown"
	 ::={panCommonEventEventsV2 831}

	 panHANfsPanlogsFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "NFS panlogs failure"
	 ::={panCommonEventEventsV2 832}

	 panHAInternalHaErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA is not working properly; please call support"
	 ::={panCommonEventEventsV2 833}

	 panHASystemFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "System failure"
	 ::={panCommonEventEventsV2 834}

	 panHAHa2KeepAliveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA2 keep alive status to peer device changed"
	 ::={panCommonEventEventsV2 835}

	 panHASlotFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot in failure state"
	 ::={panCommonEventEventsV2 836}

	 panHASlotMismatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot(s) in mismatch state"
	 ::={panCommonEventEventsV2 837}

	 panHASlotControlFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot ha-pair command failure"
	 ::={panCommonEventEventsV2 838}

	 panHASlotControlEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot ha-pair command event"
	 ::={panCommonEventEventsV2 839}

	 panHASessionSynchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Session synchronization messages"
	 ::={panCommonEventEventsV2 840}

	 panHAVmAwsInterfaceTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "AWS VM interface error"
	 ::={panCommonEventEventsV2 841}

	 panHWDiskErrorsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Hard drive physical issues"
	 ::={panCommonEventEventsV2 900}

	 panHWSlotUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot is up and functional"
	 ::={panCommonEventEventsV2 901}

	 panHWInsufficientPowerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Not enough power to start slot"
	 ::={panCommonEventEventsV2 902}

	 panHWSlotUnsupportedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Not supported card detected"
	 ::={panCommonEventEventsV2 903}

	 panHWSlotStartingTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot is starting"
	 ::={panCommonEventEventsV2 904}

	 panHWSlotStoppingTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot is stopping"
	 ::={panCommonEventEventsV2 905}

	 panHWSlotFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot has seen a failure"
	 ::={panCommonEventEventsV2 906}

	 panHWSlotPoweroffTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot is powered off"
	 ::={panCommonEventEventsV2 907}

	 panHWSlotAdminpoweroffTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Slot is admin-powered off"
	 ::={panCommonEventEventsV2 908}

	 panHWSlotInsertedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Card inserted in slot"
	 ::={panCommonEventEventsV2 909}

	 panHWSlotRemovedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Card removed from slot"
	 ::={panCommonEventEventsV2 910}

	 panHWPsInsertedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Power supply inserted"
	 ::={panCommonEventEventsV2 911}

	 panHWPsRemovedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Power supply removed"
	 ::={panCommonEventEventsV2 912}

	 panHWPsFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Power supply failure"
	 ::={panCommonEventEventsV2 913}

	 panHWFanInsertedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Fan tray inserted"
	 ::={panCommonEventEventsV2 914}

	 panHWFanRemovedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Fan tray removed"
	 ::={panCommonEventEventsV2 915}

	 panHWFanFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Fan failure"
	 ::={panCommonEventEventsV2 916}

	 panHWBootstrapImageErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Booting from external device image failed, bootstrap aborted"
	 ::={panCommonEventEventsV2 917}

	 panHWBootstrapConfigNotFoundTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "No bootstrap config found on the external device"
	 ::={panCommonEventEventsV2 918}

	 panHWBadParamsBootstrapConfigTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Missing or incorrect mandatory parameters in the bootstrap config file"
	 ::={panCommonEventEventsV2 919}

	 panHWMediaSanityFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Install media failed sanity check"
	 ::={panCommonEventEventsV2 920}

	 panHWUsbMediaPrepSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "USB media prepared successfully using given bundle"
	 ::={panCommonEventEventsV2 921}

	 panHWBootstrapSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Bootstrap completed successfully from external device"
	 ::={panCommonEventEventsV2 922}

	 panHWBootstrapLicenseFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "License installation failed for bootstrap device"
	 ::={panCommonEventEventsV2 923}

	 panHWBootstrapContentFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Content installation failed for bootstrap device"
	 ::={panCommonEventEventsV2 924}

	 panHWBootstrapMediaDetectTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Bootstrap install media detect status"
	 ::={panCommonEventEventsV2 925}

	 panHWBootstrapMediaSanityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Bootstrap install media sanity check status"
	 ::={panCommonEventEventsV2 926}

	 panHWBootstrapImageUpgradeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Bootstrap software image installation status"
	 ::={panCommonEventEventsV2 927}

	 panHWBootstrapOpCmdTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Bootstrap operational command status"
	 ::={panCommonEventEventsV2 928}

	 panHWThermalFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "I2C Failure"
	 ::={panCommonEventEventsV2 929}

	 panHWContentEngineFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CE Memory Failure"
	 ::={panCommonEventEventsV2 930}

	 panHWFailoverCLITrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Planned SC Failover"
	 ::={panCommonEventEventsV2 931}

	 panHWFailoverUnexpectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Unexpected SC Failover"
	 ::={panCommonEventEventsV2 932}

	 panNTDPRestartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Restarted ntpd"
	 ::={panCommonEventEventsV2 1000}

	 panNTDPTimeLearnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Restarted ntpd on config change"
	 ::={panCommonEventEventsV2 1001}

	 panNTDPSyncTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "sync to server"
	 ::={panCommonEventEventsV2 1002}

	 panNTDPAuthTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "authentication"
	 ::={panCommonEventEventsV2 1003}

	 panPBFNhUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PBF nexthop is reachable"
	 ::={panCommonEventEventsV2 1100}

	 panPBFNhDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PBF nexthop is unreachable"
	 ::={panCommonEventEventsV2 1101}

	 panPBFPbfFqdnDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PBF nexthop fqdn mapping is unresolved"
	 ::={panCommonEventEventsV2 1102}

	 panPBFPbfFqdnChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PBF nexthop fqdn mapping is changed"
	 ::={panCommonEventEventsV2 1103}

	 panPORTLinkChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Interface link state change"
	 ::={panCommonEventEventsV2 1200}

	 panPORTNonqualSfpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Non-qualified SFP inserted"
	 ::={panCommonEventEventsV2 1201}

	 panPORTNonqualSfpPlusTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Non-qualified SFP-plus inserted"
	 ::={panCommonEventEventsV2 1202}

	 panPORTNonqualXfpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Non-qualified XFP inserted"
	 ::={panCommonEventEventsV2 1203}

	 panPORTNonsuppForcedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Non-supported forced mode configured"
	 ::={panCommonEventEventsV2 1204}

	 panPORTInvalidModuleTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Invalid pluggable module inserted"
	 ::={panCommonEventEventsV2 1205}

	 panPORTSdwanLinkChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SD-WAN Interface link state change"
	 ::={panCommonEventEventsV2 1206}

	 panPPPOEInitiateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE initiated"
	 ::={panCommonEventEventsV2 1300}

	 panPPPOEConnectTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE connected"
	 ::={panCommonEventEventsV2 1301}

	 panPPPOEConnectFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE failed to connect"
	 ::={panCommonEventEventsV2 1302}

	 panPPPOETerminateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE terminated"
	 ::={panCommonEventEventsV2 1303}

	 panPPPOEIfUpdateFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE interface update failed"
	 ::={panCommonEventEventsV2 1304}

	 panPPPOEDontSendEolPadiTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE Don't Send EOL Tag in PADI packet"
	 ::={panCommonEventEventsV2 1305}

	 panPPPOEDontSendEolPadrTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE Don't Send EOL Tag in PADR packet"
	 ::={panCommonEventEventsV2 1306}

	 panPPPOEAddressTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PPPOE slaac address selection"
	 ::={panCommonEventEventsV2 1307}

	 panPPPOEV6IfUpdateFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 update fail"
	 ::={panCommonEventEventsV2 1308}

	 panPPPOEV6IfUpdateOkTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 update successful"
	 ::={panCommonEventEventsV2 1309}

	 panPPPOEV6IfClearTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 info cleared"
	 ::={panCommonEventEventsV2 1310}

	 panPPPOEV6IfRenewTriggerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 renew triggered"
	 ::={panCommonEventEventsV2 1311}

	 panPPPOEV6IfReleaseTriggerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 release triggered"
	 ::={panCommonEventEventsV2 1312}

	 panPPPOEV6IfConfirmFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 confirm failed,continuing with the existing addresses"
	 ::={panCommonEventEventsV2 1313}

	 panPPPOEV6IfDuplicateIpIntfTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 received IP address already assigned to another interface"
	 ::={panCommonEventEventsV2 1314}

	 panPPPOEV6IfDuplicateIpRemoteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 received IP address already used by another host on the network"
	 ::={panCommonEventEventsV2 1315}

	 panPPPOEV6IfIanaNotReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 unable to obtain Non-temporary address from the Server"
	 ::={panCommonEventEventsV2 1316}

	 panPPPOEV6IfIataNotReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 unable to obtain Temporary address from the Server"
	 ::={panCommonEventEventsV2 1317}

	 panPPPOEV6IfIapdNotReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 unable to obtain Prefix Delegation address from the Server"
	 ::={panCommonEventEventsV2 1318}

	 panPPPOEV6IfDhcpv6LeaseStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 lease of addresses started"
	 ::={panCommonEventEventsV2 1319}

	 panPPPOEV6IfDhcpv6PreferredLifetimeOverTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Preferred lifetime of addresses expired"
	 ::={panCommonEventEventsV2 1320}

	 panPPPOEV6IfDhcpv6LeaseEndTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Lease of addresses"
	 ::={panCommonEventEventsV2 1321}

	 panPPPOEV6IfDuplicateAddressReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 IPv6 address ip_address on interface if_name failed due to duplicate IP check"
	 ::={panCommonEventEventsV2 1322}

	 panPPPOEV6IfPdIdentifierValueTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Prefix cannot be assigned to the Inherited Interface if_name,since the value of the Pool identifier is larger the prefix range received."
	 ::={panCommonEventEventsV2 1323}

	 panPPPOEV6IfPdExhaustTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DHCPV6 Prefix cannot be assigned to the Inherited Interface,since the prefix pool exhausted."
	 ::={panCommonEventEventsV2 1324}

	 panRASRasmgrConfigP1SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon configuration load phase-1 succeeded."
	 ::={panCommonEventEventsV2 1400}

	 panRASRasmgrConfigP1FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon configuration load phase-1 failed."
	 ::={panCommonEventEventsV2 1401}

	 panRASRasmgrConfigP1AbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon configuration load phase-1 aborted."
	 ::={panCommonEventEventsV2 1402}

	 panRASRasmgrConfigP2SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon configuration load phase-2 succeeded."
	 ::={panCommonEventEventsV2 1403}

	 panRASRasmgrConfigP2FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon configuration load phase-2 failed."
	 ::={panCommonEventEventsV2 1404}

	 panRASRasmgrDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon is ready."
	 ::={panCommonEventEventsV2 1405}

	 panRASRasmgrDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon has exited."
	 ::={panCommonEventEventsV2 1406}

	 panRASRasmgrDaemonInitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon is initializing."
	 ::={panCommonEventEventsV2 1407}

	 panRASRasmgrFlowFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon sync all user info to Flow started."
	 ::={panCommonEventEventsV2 1408}

	 panRASRasmgrFlowFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon sync all user info to Flow no longer needed."
	 ::={panCommonEventEventsV2 1409}

	 panRASRasmgrFlowFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon sync all user info to Flow exit."
	 ::={panCommonEventEventsV2 1410}

	 panRASRasmgrHaFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon sync all user info to HA peer started."
	 ::={panCommonEventEventsV2 1411}

	 panRASRasmgrHaFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon sync all user info to HA peer no longer needed."
	 ::={panCommonEventEventsV2 1412}

	 panRASRasmgrHaFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RASMGR daemon sync all user info to HA peer exit."
	 ::={panCommonEventEventsV2 1413}

	 panROUTINGRoutedConfigP1SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon configuration load phase-1 succeeded."
	 ::={panCommonEventEventsV2 1500}

	 panROUTINGRoutedConfigP1FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon configuration load phase-1 failed."
	 ::={panCommonEventEventsV2 1501}

	 panROUTINGRoutedConfigP1AbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon configuration load phase-1 aborted."
	 ::={panCommonEventEventsV2 1502}

	 panROUTINGRoutedConfigP2SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon configuration load phase-2 succeeded."
	 ::={panCommonEventEventsV2 1503}

	 panROUTINGRoutedConfigP2FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon configuration load phase-2 failed."
	 ::={panCommonEventEventsV2 1504}

	 panROUTINGRoutedDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon is ready."
	 ::={panCommonEventEventsV2 1505}

	 panROUTINGRoutedDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon has exited."
	 ::={panCommonEventEventsV2 1506}

	 panROUTINGRoutedDaemonInitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route daemon is initializing."
	 ::={panCommonEventEventsV2 1507}

	 panROUTINGRoutedFibSyncPeerBackupTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "FIB HA sync started when peer device becomes passive."
	 ::={panCommonEventEventsV2 1508}

	 panROUTINGRoutedFibSyncSelfMasterTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "FIB HA sync started when local device becomes master."
	 ::={panCommonEventEventsV2 1509}

	 panROUTINGRoutedRTMBadRouteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "An invalid dynamic route has been rejected:"
	 ::={panCommonEventEventsV2 1510}

	 panROUTINGRoutedOSPFLSAChksumFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF LSA checksum generating failed due to memory corruption."
	 ::={panCommonEventEventsV2 1511}

	 panROUTINGRoutedOSPFLSAChksumInvalidTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF received LSA with invalid checksum."
	 ::={panCommonEventEventsV2 1512}

	 panROUTINGRoutedOSPFAuthtypeBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to unexpected authentication type."
	 ::={panCommonEventEventsV2 1513}

	 panROUTINGRoutedOSPFPasswordBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect simple password."
	 ::={panCommonEventEventsV2 1514}

	 panROUTINGRoutedOSPFChksumBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect OSPF checksum."
	 ::={panCommonEventEventsV2 1515}

	 panROUTINGRoutedOSPFSequenceBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect sequence number."
	 ::={panCommonEventEventsV2 1516}

	 panROUTINGRoutedOSPFMd5chksumBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect MD5 checksum."
	 ::={panCommonEventEventsV2 1517}

	 panROUTINGRoutedOSPFMd5lengthBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect MD5 digest length."
	 ::={panCommonEventEventsV2 1518}

	 panROUTINGRoutedOSPFHelloHelloIntvalBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to hello-interval mismatch."
	 ::={panCommonEventEventsV2 1519}

	 panROUTINGRoutedOSPFHelloDeadIntvalBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to dead-interval mismatch."
	 ::={panCommonEventEventsV2 1520}

	 panROUTINGRoutedOSPFHelloNetmaskBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to network masks mismatch."
	 ::={panCommonEventEventsV2 1521}

	 panROUTINGRoutedOSPFHelloAreaTypeBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to area type mismatch."
	 ::={panCommonEventEventsV2 1522}

	 panROUTINGRoutedOSPFNeighbor2dirTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF two-way communication established with neighbor."
	 ::={panCommonEventEventsV2 1523}

	 panROUTINGRoutedOSPFNeighborFullTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF full adjacency established with neighbor."
	 ::={panCommonEventEventsV2 1524}

	 panROUTINGRoutedOSPFNeighborDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF adjacency with neighbor has gone down."
	 ::={panCommonEventEventsV2 1525}

	 panROUTINGRoutedRIPPeerAddTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP peer discovered."
	 ::={panCommonEventEventsV2 1526}

	 panROUTINGRoutedRIPPeerDelTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP peer disappeared."
	 ::={panCommonEventEventsV2 1527}

	 panROUTINGRoutedRIPAuthtypeBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP packet dropped due to unexpected authentication type."
	 ::={panCommonEventEventsV2 1528}

	 panROUTINGRoutedRIPAuthFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP packet dropped due to authentication failure."
	 ::={panCommonEventEventsV2 1529}

	 panROUTINGRoutedRIPMd5lengthBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP packet dropped due to incorrect MD5 digest length."
	 ::={panCommonEventEventsV2 1530}

	 panROUTINGRoutedBGPPeerEnterEstablishedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer session enters established state."
	 ::={panCommonEventEventsV2 1531}

	 panROUTINGRoutedBGPPeerLeftEstablishedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer session left established state."
	 ::={panCommonEventEventsV2 1532}

	 panROUTINGRoutedBGPPeerFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer session has failed and may restart."
	 ::={panCommonEventEventsV2 1533}

	 panROUTINGRoutedBGPPeerRestartedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Initiated graceful-restart with a BGP peer."
	 ::={panCommonEventEventsV2 1534}

	 panROUTINGRoutedBGPPeerRestartFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Graceful-restart with a BGP peer failed."
	 ::={panCommonEventEventsV2 1535}

	 panROUTINGRoutedBGPRefreshSentTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ROUTE REFRESH message sent to a BGP peer."
	 ::={panCommonEventEventsV2 1536}

	 panROUTINGRoutedBGPRibinRecalcTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "An RIB-In is being recalculated as a result of changed import policy."
	 ::={panCommonEventEventsV2 1537}

	 panROUTINGRoutedPIMInterfaceStateChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM interface state changed"
	 ::={panCommonEventEventsV2 1538}

	 panROUTINGRoutedPIMNewDrElectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM elected a new DR"
	 ::={panCommonEventEventsV2 1539}

	 panROUTINGRoutedPIMNeighborDiscoveredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM discovered a new neighbor"
	 ::={panCommonEventEventsV2 1540}

	 panROUTINGRoutedPIMNeighborDisappearedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM neighbor disappeared"
	 ::={panCommonEventEventsV2 1541}

	 panROUTINGRoutedIGMPWrongVersionTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Wrong IGMP query version"
	 ::={panCommonEventEventsV2 1542}

	 panROUTINGRoutedGenericEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1543}

	 panROUTINGRoutedOSPFStartGracefulRestartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF started graceful restart."
	 ::={panCommonEventEventsV2 1544}

	 panROUTINGRoutedOSPFStoppedGracefulRestartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF stopped graceful restart."
	 ::={panCommonEventEventsV2 1545}

	 panROUTINGRoutedOSPFStartHelperNodeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF started helper mode for a restarting neighbor."
	 ::={panCommonEventEventsV2 1546}

	 panROUTINGRoutedOSPFStopHelperModeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF stopped helper mode for a restarting neighbor."
	 ::={panCommonEventEventsV2 1547}

	 panROUTINGRoutedOSPFNotHelpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF did not help a restarting neighbor."
	 ::={panCommonEventEventsV2 1548}

	 panROUTINGRoutedECMPTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1549}

	 panROUTINGRoutedBGPPeerMpExtensionNegotiateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer MP extension negotiation."
	 ::={panCommonEventEventsV2 1550}

	 panROUTINGPathMonitorFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Path monitoring failed for static route, route removed."
	 ::={panCommonEventEventsV2 1551}

	 panROUTINGPathMonitorRecoveryTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Path monitoring recovered for static route, route restored."
	 ::={panCommonEventEventsV2 1552}

	 panROUTINGRouteTableCapacityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Route table capacity reached."
	 ::={panCommonEventEventsV2 1553}

	 panROUTINGBGPRibInCapacityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer prefix capacity reached."
	 ::={panCommonEventEventsV2 1554}

	 panROUTINGRoutedBgpFqdnChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Routed BGP fqdn mapping is changed"
	 ::={panCommonEventEventsV2 1555}

	 panROUTINGRoutedStaticFqdnChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Routed static fqdn mapping is changed"
	 ::={panCommonEventEventsV2 1556}

	 panROUTINGRoutedBgpFqdnDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Routed BGP fqdn mapping is unresolved"
	 ::={panCommonEventEventsV2 1557}

	 panROUTINGRoutedStaticFqdnDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Routed static fqdn mapping is unresolved"
	 ::={panCommonEventEventsV2 1558}

	 panROUTINGRoutedZEBRALogTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ZEBRA LOG : "
	 ::={panCommonEventEventsV2 1559}

	 panROUTINGRoutedSTATICLogTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "STATIC LOG : "
	 ::={panCommonEventEventsV2 1560}

	 panROUTINGRoutedOSPFLSAChksumFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF LSA checksum generating failed due to memory corruption."
	 ::={panCommonEventEventsV2 1561}

	 panROUTINGRoutedOSPFLSAChksumInvalidTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF received LSA with invalid checksum."
	 ::={panCommonEventEventsV2 1562}

	 panROUTINGRoutedOSPFAuthtypeBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to unexpected authentication type."
	 ::={panCommonEventEventsV2 1563}

	 panROUTINGRoutedOSPFPasswordBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect simple password."
	 ::={panCommonEventEventsV2 1564}

	 panROUTINGRoutedOSPFChksumBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect OSPF checksum."
	 ::={panCommonEventEventsV2 1565}

	 panROUTINGRoutedOSPFSequenceBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect sequence number."
	 ::={panCommonEventEventsV2 1566}

	 panROUTINGRoutedOSPFMd5chksumBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect MD5 checksum."
	 ::={panCommonEventEventsV2 1567}

	 panROUTINGRoutedOSPFMd5lengthBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF packet dropped due to incorrect MD5 digest length."
	 ::={panCommonEventEventsV2 1568}

	 panROUTINGRoutedOSPFHelloHelloIntvalBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to hello-interval mismatch."
	 ::={panCommonEventEventsV2 1569}

	 panROUTINGRoutedOSPFHelloDeadIntvalBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to dead-interval mismatch."
	 ::={panCommonEventEventsV2 1570}

	 panROUTINGRoutedOSPFHelloNetmaskBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to network masks mismatch."
	 ::={panCommonEventEventsV2 1571}

	 panROUTINGRoutedOSPFHelloAreaTypeBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF hello packet dropped due to area type mismatch."
	 ::={panCommonEventEventsV2 1572}

	 panROUTINGRoutedOSPFNeighbor2dirTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF two-way communication established with neighbor."
	 ::={panCommonEventEventsV2 1573}

	 panROUTINGRoutedOSPFNeighborFullTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF full adjacency established with neighbor."
	 ::={panCommonEventEventsV2 1574}

	 panROUTINGRoutedOSPFNeighborDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF adjacency with neighbor has gone down."
	 ::={panCommonEventEventsV2 1575}

	 panROUTINGRoutedOSPFStartGracefulRestartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF started graceful restart."
	 ::={panCommonEventEventsV2 1576}

	 panROUTINGRoutedOSPFStoppedGracefulRestartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF stopped graceful restart."
	 ::={panCommonEventEventsV2 1577}

	 panROUTINGRoutedOSPFStartHelperNodeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF started helper mode for a restarting neighbor."
	 ::={panCommonEventEventsV2 1578}

	 panROUTINGRoutedOSPFStopHelperModeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF stopped helper mode for a restarting neighbor."
	 ::={panCommonEventEventsV2 1579}

	 panROUTINGRoutedOSPFNotHelpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "OSPF did not help a restarting neighbor."
	 ::={panCommonEventEventsV2 1580}

	 panROUTINGRoutedRIPPeerAddTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP peer discovered."
	 ::={panCommonEventEventsV2 1581}

	 panROUTINGRoutedRIPPeerDelTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP peer disappeared."
	 ::={panCommonEventEventsV2 1582}

	 panROUTINGRoutedRIPAuthtypeBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP packet dropped due to unexpected authentication type."
	 ::={panCommonEventEventsV2 1583}

	 panROUTINGRoutedRIPAuthFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP packet dropped due to authentication failure."
	 ::={panCommonEventEventsV2 1584}

	 panROUTINGRoutedRIPMd5lengthBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RIP packet dropped due to incorrect MD5 digest length."
	 ::={panCommonEventEventsV2 1585}

	 panROUTINGBGPRTMCapacityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "New BGP route exceeded RTM capacity."
	 ::={panCommonEventEventsV2 1586}

	 panROUTINGRoutedBGPPeerEnterEstablishedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer session enters established state."
	 ::={panCommonEventEventsV2 1587}

	 panROUTINGRoutedBGPPeerLeftEstablishedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer session left established state."
	 ::={panCommonEventEventsV2 1588}

	 panROUTINGRoutedBGPPeerMpExtensionNegotiateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer MP extension negotiation."
	 ::={panCommonEventEventsV2 1589}

	 panROUTINGRoutedBGPPeerFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer session has failed and may restart."
	 ::={panCommonEventEventsV2 1590}

	 panROUTINGRoutedBGPPeerRestartedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Initiated graceful-restart with a BGP peer."
	 ::={panCommonEventEventsV2 1591}

	 panROUTINGRoutedBGPPeerRestartFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Graceful-restart with a BGP peer failed."
	 ::={panCommonEventEventsV2 1592}

	 panROUTINGRoutedBGPPeerPrefixExceededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BGP peer advertised more than maximum allowed prefixes."
	 ::={panCommonEventEventsV2 1593}

	 panROUTINGRoutedBGPRefreshSentTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ROUTE REFRESH message sent to a BGP peer."
	 ::={panCommonEventEventsV2 1594}

	 panROUTINGRoutedBGPRibinRecalcTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "An RIB-In is being recalculated as a result of changed import policy."
	 ::={panCommonEventEventsV2 1595}

	 panROUTINGRoutedBGPRiboutRecalcTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "An RIB-Out is being recalculated as a result of changed export policy."
	 ::={panCommonEventEventsV2 1596}

	 panROUTINGRoutedPIMInterfaceStateChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM interface state changed"
	 ::={panCommonEventEventsV2 1597}

	 panROUTINGRoutedPIMNewDrElectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM elected a new DR"
	 ::={panCommonEventEventsV2 1598}

	 panROUTINGRoutedPIMNeighborDiscoveredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM discovered a new neighbor"
	 ::={panCommonEventEventsV2 1599}

	 panROUTINGRoutedPIMNeighborDisappearedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PIM neighbor disappeared"
	 ::={panCommonEventEventsV2 1600}

	 panROUTINGRoutedIGMPWrongVersionTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Wrong IGMP query version"
	 ::={panCommonEventEventsV2 1601}

	 panROUTINGRoutedMSDPPeerCreatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1602}

	 panROUTINGRoutedMSDPPeerDeletedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1603}

	 panROUTINGRoutedMSDPPeerStateChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1604}

	 panROUTINGRoutedSACreatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1605}

	 panROUTINGRoutedSADeletedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1606}

	 panROUTINGRoutedSARejectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1607}

	 panROUTINGRoutedSAFilteredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1608}

	 panSSLVPNSslvpnRegistSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN user login succeeded."
	 ::={panCommonEventEventsV2 1600}

	 panSSLVPNSslvpnRegistFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN user login failed."
	 ::={panCommonEventEventsV2 1601}

	 panSSLVPNSslvpnLogoutSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN user logout succeeded."
	 ::={panCommonEventEventsV2 1602}

	 panSSLVPNSslvpnLogoutFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN user logout failed."
	 ::={panCommonEventEventsV2 1603}

	 panSSLVPNSslvpnConfigSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN client configuration generated."
	 ::={panCommonEventEventsV2 1604}

	 panSSLVPNSslvpnConfigFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN client configuration failed."
	 ::={panCommonEventEventsV2 1605}

	 panSSLVPNSslvpnConfigReleaseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN client configuration released."
	 ::={panCommonEventEventsV2 1606}

	 panSSLVPNSslvpnSwitchSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN client switch to SSL tunnel mode succeeded."
	 ::={panCommonEventEventsV2 1607}

	 panSSLVPNSslvpnSwitchFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN client switch to SSL tunnel mode failed."
	 ::={panCommonEventEventsV2 1608}

	 panSSLVPNSslvpnAuthSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN user authentication succeeded."
	 ::={panCommonEventEventsV2 1609}

	 panSSLVPNSslvpnAuthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL VPN user authentication failed."
	 ::={panCommonEventEventsV2 1610}

	 panVPNIkeConfigP1SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon configuration load phase-1 succeeded."
	 ::={panCommonEventEventsV2 1700}

	 panVPNIkeConfigP1FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon configuration load phase-1 failed."
	 ::={panCommonEventEventsV2 1701}

	 panVPNIkeConfigP1AbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon configuration load phase-1 aborted."
	 ::={panCommonEventEventsV2 1702}

	 panVPNIkeConfigP2SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon configuration load phase-2 succeeded."
	 ::={panCommonEventEventsV2 1703}

	 panVPNIkeConfigP2FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon configuration load phase-2 failed."
	 ::={panCommonEventEventsV2 1704}

	 panVPNIkeDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon is ready."
	 ::={panCommonEventEventsV2 1705}

	 panVPNIkeDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon has exited."
	 ::={panCommonEventEventsV2 1706}

	 panVPNIkeDaemonInitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE daemon is initializing."
	 ::={panCommonEventEventsV2 1707}

	 panVPNIkeNegoP1StartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is started"
	 ::={panCommonEventEventsV2 1708}

	 panVPNIkeNegoP1FailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is failed"
	 ::={panCommonEventEventsV2 1709}

	 panVPNIkeNegoP1SuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is succeeded"
	 ::={panCommonEventEventsV2 1710}

	 panVPNIkeNegoP1ExpireTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 SA is expired"
	 ::={panCommonEventEventsV2 1711}

	 panVPNIkeNegoP1DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 SA is deleted"
	 ::={panCommonEventEventsV2 1712}

	 panVPNIkeNegoP1DpdDnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 SA is down determined by DPD."
	 ::={panCommonEventEventsV2 1713}

	 panVPNIkeNegoP1PskIdtypeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is failed. When pre-shared key is used peer-ID must be type IP address."
	 ::={panCommonEventEventsV2 1714}

	 panVPNIkeNegoP1FailPskTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is failed likely due to pre-shared key mismatch."
	 ::={panCommonEventEventsV2 1715}

	 panVPNIkeNegoP1FailCommonTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is failed."
	 ::={panCommonEventEventsV2 1716}

	 panVPNIkeNegoP2StartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation is started"
	 ::={panCommonEventEventsV2 1717}

	 panVPNIkeNegoP2FailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation is failed"
	 ::={panCommonEventEventsV2 1718}

	 panVPNIkeNegoP2SuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation is succeeded"
	 ::={panCommonEventEventsV2 1719}

	 panVPNIkeNegoP2StaleP1Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Deleting a possible stale phase-1 SA."
	 ::={panCommonEventEventsV2 1720}

	 panVPNIkeNegoP2DupRekeyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "duplicate phase-2 rekey request detected ignore new request."
	 ::={panCommonEventEventsV2 1721}

	 panVPNIkeNegoP2SimulContTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "simultaneous phase-2 rekey request detected peer is PANOS. Ignore this new request."
	 ::={panCommonEventEventsV2 1722}

	 panVPNIkeNegoP2SimulFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "simultaneous phase-2 rekey request detected peer is PANOS. Previous request removed."
	 ::={panCommonEventEventsV2 1723}

	 panVPNIkeNegoP2SimulDelayTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "simultaneous phase-2 rekey request detected peer is not PANOS. Delay processing this new request."
	 ::={panCommonEventEventsV2 1724}

	 panVPNIkeNegoP2NoP1Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation request received but no phase-1 SA is found."
	 ::={panCommonEventEventsV2 1725}

	 panVPNIkeNegoP2P1NotReadyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation request received but no active phase-1 SA is available."
	 ::={panCommonEventEventsV2 1726}

	 panVPNIkeNegoP2ProxyIdBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation failed when processing proxy ID."
	 ::={panCommonEventEventsV2 1727}

	 panVPNIkeNegoP2ProposalBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-2 negotiation failed when processing SA payload."
	 ::={panCommonEventEventsV2 1728}

	 panVPNIpsecKeyInstallTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IPSec key installed."
	 ::={panCommonEventEventsV2 1729}

	 panVPNIpsecKeyDeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IPSec key deleted."
	 ::={panCommonEventEventsV2 1730}

	 panVPNIpsecKeyExpireTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IPSec key lifetime expired."
	 ::={panCommonEventEventsV2 1731}

	 panVPNIkeRecvNotifyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE protocol notification message received:"
	 ::={panCommonEventEventsV2 1732}

	 panVPNIkeRecvP1DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE protocol phase-1 SA delete message received from peer."
	 ::={panCommonEventEventsV2 1733}

	 panVPNIkeRecvP2DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE protocol IPSec SA delete message received from peer."
	 ::={panCommonEventEventsV2 1734}

	 panVPNIkeSendNotifyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE protocol notification message sent:"
	 ::={panCommonEventEventsV2 1735}

	 panVPNIkeSendP1DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE protocol phase-1 SA delete message sent to peer."
	 ::={panCommonEventEventsV2 1736}

	 panVPNIkeSendP2DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE protocol IPSec SA delete message sent to peer."
	 ::={panCommonEventEventsV2 1737}

	 panVPNIkev2NegoIkeStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA negotiation is started"
	 ::={panCommonEventEventsV2 1738}

	 panVPNIkev2NegoIkeFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA negotiation is failed"
	 ::={panCommonEventEventsV2 1739}

	 panVPNIkev2NegoIkeSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA negotiation is succeeded"
	 ::={panCommonEventEventsV2 1740}

	 panVPNIkev2NegoIkeExpireTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA is expired"
	 ::={panCommonEventEventsV2 1741}

	 panVPNIkev2NegoIkeDeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA is deleted"
	 ::={panCommonEventEventsV2 1742}

	 panVPNIkev2NegoChildStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 Child SA negotiation is started"
	 ::={panCommonEventEventsV2 1743}

	 panVPNIkev2NegoChildFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 Child SA negotiation is failed"
	 ::={panCommonEventEventsV2 1744}

	 panVPNIkev2NegoChildSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 Child SA negotiation is succeeded"
	 ::={panCommonEventEventsV2 1745}

	 panVPNTunnelStatusUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Tunnel status change to UP."
	 ::={panCommonEventEventsV2 1746}

	 panVPNTunnelStatusDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Tunnel status change to DOWN."
	 ::={panCommonEventEventsV2 1747}

	 panVPNKeymgrDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR daemon is ready."
	 ::={panCommonEventEventsV2 1748}

	 panVPNKeymgrDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR daemon has exited."
	 ::={panCommonEventEventsV2 1749}

	 panVPNKeymgrDaemonInitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR daemon is initializing."
	 ::={panCommonEventEventsV2 1750}

	 panVPNKeymgrFlowFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to Flow started."
	 ::={panCommonEventEventsV2 1751}

	 panVPNKeymgrFlowFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to Flow no longer needed."
	 ::={panCommonEventEventsV2 1752}

	 panVPNKeymgrFlowFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to Flow exit."
	 ::={panCommonEventEventsV2 1753}

	 panVPNKeymgrIkeFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to IKE daemon started."
	 ::={panCommonEventEventsV2 1754}

	 panVPNKeymgrIkeFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to IKE daemon no longer needed."
	 ::={panCommonEventEventsV2 1755}

	 panVPNKeymgrIkeFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to IKE daemon exit."
	 ::={panCommonEventEventsV2 1756}

	 panVPNKeymgrHaFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to HA peer started."
	 ::={panCommonEventEventsV2 1757}

	 panVPNKeymgrHaFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to HA peer no longer needed."
	 ::={panCommonEventEventsV2 1758}

	 panVPNKeymgrHaFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "KEYMGR sync all IPSec SA to HA peer exit."
	 ::={panCommonEventEventsV2 1759}

	 panVPNIkeGenericEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1760}

	 panVPNKeymgrGenericEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1761}

	 panVPNIkeNegoP1FailCertTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation is failed."
	 ::={panCommonEventEventsV2 1762}

	 panVPNIkeNegoP1CertIdMismatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE phase-1 negotiation failed."
	 ::={panCommonEventEventsV2 1763}

	 panVPNIkeNegoP1CertSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE certificate authentication succeeded."
	 ::={panCommonEventEventsV2 1764}

	 panVPNIkev2NegoIkeDpdDnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA is down determined by DPD."
	 ::={panCommonEventEventsV2 1765}

	 panVPNIkev2NegoPskIdtypeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 SA negotiation is failed. When pre-shared key is used, peer-ID must be type IP address."
	 ::={panCommonEventEventsV2 1766}

	 panVPNIkev2NegoFailPskTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 SA negotiation is failed likely due to pre-shared key mismatch."
	 ::={panCommonEventEventsV2 1767}

	 panVPNIkev2NegoFailCommonTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 SA negotiation is failed."
	 ::={panCommonEventEventsV2 1768}

	 panVPNIkev2NegoFailCertTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 certificate authentication failed."
	 ::={panCommonEventEventsV2 1769}

	 panVPNIkev2NegoCertIdMismatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 SA negotiation failed."
	 ::={panCommonEventEventsV2 1770}

	 panVPNIkev2NegoCertSuccTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 certificate authentication succeeded."
	 ::={panCommonEventEventsV2 1771}

	 panVPNIkev2NegoUseV1Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv1 is used in IKEv2 preferred mode."
	 ::={panCommonEventEventsV2 1772}

	 panVPNIkev2NegoStaleP1Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Deleting a possible stale IKE SA."
	 ::={panCommonEventEventsV2 1773}

	 panVPNIkev2NegoStaleP2Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Deleting a possible stale IKEv2 child SA."
	 ::={panCommonEventEventsV2 1774}

	 panVPNIkev2NegoChildDupRekeyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "duplicate child SA rekey request detected, ignore new request."
	 ::={panCommonEventEventsV2 1775}

	 panVPNIkev2NegoChildSimulContTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "simultaneous child SA rekey request detected, peer is PANOS. Ignore this new request."
	 ::={panCommonEventEventsV2 1776}

	 panVPNIkev2NegoChildSimulFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "simultaneous child SA rekey request detected, peer is PANOS. Previous request removed."
	 ::={panCommonEventEventsV2 1777}

	 panVPNIkev2NegoChildSimulDelayTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "simultaneous child SA rekey request detected, peer is not PANOS. Delay processing this new request."
	 ::={panCommonEventEventsV2 1778}

	 panVPNIkev2NegoChildNoP1Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 child SA negotiation request received but no IKE SA is found."
	 ::={panCommonEventEventsV2 1779}

	 panVPNIkev2NegoChildP1NotReadyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 child SA negotiation request received but no active IKE SA is available."
	 ::={panCommonEventEventsV2 1780}

	 panVPNIkev2NegoChildTsBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 child SA negotiation failed when processing traffic selector."
	 ::={panCommonEventEventsV2 1781}

	 panVPNIkev2NegoChildProposalBadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 child SA negotiation failed when processing SA payload."
	 ::={panCommonEventEventsV2 1782}

	 panVPNIkev2RecvNotifyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 notification message received:"
	 ::={panCommonEventEventsV2 1783}

	 panVPNIkev2RecvP1DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA delete message received from peer."
	 ::={panCommonEventEventsV2 1784}

	 panVPNIkev2RecvP2DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IPSec SA delete message received from peer."
	 ::={panCommonEventEventsV2 1785}

	 panVPNIkev2SendNotifyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 notification message sent:"
	 ::={panCommonEventEventsV2 1786}

	 panVPNIkev2SendP1DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IKE SA delete message sent to peer."
	 ::={panCommonEventEventsV2 1787}

	 panVPNIkev2SendP2DeleteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 IPSec SA delete message sent to peer."
	 ::={panCommonEventEventsV2 1788}

	 panVPNSdwanTunnelStatusUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SD-WAN Tunnel status change to UP."
	 ::={panCommonEventEventsV2 1789}

	 panVPNSdwanTunnelStatusDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SD-WAN Tunnel status change to DOWN."
	 ::={panCommonEventEventsV2 1790}

	 panVPNIkeFqdnDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE fqdn mapping is unresolved"
	 ::={panCommonEventEventsV2 1791}

	 panVPNIkeFqdnChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKE fqdn mapping is changed"
	 ::={panCommonEventEventsV2 1792}

	 panVPNIkev2NegoFailFipsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IKEv2 FIPS Security strength check failed."
	 ::={panCommonEventEventsV2 1793}

	 panVPNVpnctlGenericEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "generic event"
	 ::={panCommonEventEventsV2 1794}

	 panVPNVpnctlIkeUpdownEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ike SA updown"
	 ::={panCommonEventEventsV2 1795}

	 panVPNVpnctlIkeRekeyEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ike SA rekey"
	 ::={panCommonEventEventsV2 1796}

	 panVPNVpnctlChildUpdownEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "child SA updown"
	 ::={panCommonEventEventsV2 1797}

	 panVPNVpnctlChildRekeyEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "child SA rekey"
	 ::={panCommonEventEventsV2 1798}

	 panSATDSatdConfigP1SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon configuration load phase-1 succeeded."
	 ::={panCommonEventEventsV2 1800}

	 panSATDSatdConfigP1FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon configuration load phase-1 failed."
	 ::={panCommonEventEventsV2 1801}

	 panSATDSatdConfigP1AbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon configuration load phase-1 aborted."
	 ::={panCommonEventEventsV2 1802}

	 panSATDSatdConfigP2SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon configuration load phase-2 succeeded."
	 ::={panCommonEventEventsV2 1803}

	 panSATDSatdConfigP2FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon configuration load phase-2 failed."
	 ::={panCommonEventEventsV2 1804}

	 panSATDSatdDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon is ready."
	 ::={panCommonEventEventsV2 1805}

	 panSATDSatdDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon has exited."
	 ::={panCommonEventEventsV2 1806}

	 panSATDSatdDaemonInitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon is initializing."
	 ::={panCommonEventEventsV2 1807}

	 panSATDSatdTunUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global Protect Site to Site Satellite tunnel is up."
	 ::={panCommonEventEventsV2 1808}

	 panSATDSatdTunDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global Protect Site to Site Satellite tunnel is down."
	 ::={panCommonEventEventsV2 1809}

	 panSATDSatdDupSubnetsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global Protect Site to Site Satellite tunnel has duplicate subnets."
	 ::={panCommonEventEventsV2 1810}

	 panSATDSatdDeniedRoutesTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global Protect Site to Site Satellite tunnel was denied routes."
	 ::={panCommonEventEventsV2 1811}

	 panSATDSatdPortalGatewayDuplicateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect portal config duplicated gateway."
	 ::={panCommonEventEventsV2 1812}

	 panSATDSatdFlowFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon sync all gateway infos to Flow started."
	 ::={panCommonEventEventsV2 1813}

	 panSATDSatdFlowFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon sync all gateway infos to Flow no longer needed."
	 ::={panCommonEventEventsV2 1814}

	 panSATDSatdFlowFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon sync all gateway infos to Flow exit."
	 ::={panCommonEventEventsV2 1815}

	 panSATDSatdHaFullSyncStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon sync all gateway infos to HA peer started."
	 ::={panCommonEventEventsV2 1816}

	 panSATDSatdHaFullSyncAbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon sync all gateway infos to HA peer no longer needed."
	 ::={panCommonEventEventsV2 1817}

	 panSATDSatdHaFullSyncDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SATD daemon sync all gateway infos to HA peer exit."
	 ::={panCommonEventEventsV2 1818}

	 panSATDSatdIpAssignFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite IP address assignment failed."
	 ::={panCommonEventEventsV2 1819}

	 panSATDSatdIpResetFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite IP address reset failed."
	 ::={panCommonEventEventsV2 1820}

	 panSATDSatdTunMonDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite Tunnel monitor down"
	 ::={panCommonEventEventsV2 1821}

	 panSATDSatdTunMonUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite Tunnel monitor up"
	 ::={panCommonEventEventsV2 1822}

	 panSATDSatdTunSoftlifetimeExpiredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite Tunnel soft lifetime expired"
	 ::={panCommonEventEventsV2 1823}

	 panSATDSatdTunHardlifetimeExpiredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite Tunnel hard lifetime expired"
	 ::={panCommonEventEventsV2 1824}

	 panSATDSatdAccRouteUpdFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite Access Routes update failed."
	 ::={panCommonEventEventsV2 1825}

	 panSATDSatdNhUpdFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect Satellite Next Hop update failed."
	 ::={panCommonEventEventsV2 1826}

	 panSATDSatdTunDpInstallErrTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Dataplane tunnel install error"
	 ::={panCommonEventEventsV2 1827}

	 panSATDSatdGatewayConnectStartedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect satellite connection to gateway started."
	 ::={panCommonEventEventsV2 1828}

	 panSATDSatdPortalConnectStartedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect satellite connection to portal started."
	 ::={panCommonEventEventsV2 1829}

	 panSATDSatdGatewayConnectFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect satellite connection to gateway failed."
	 ::={panCommonEventEventsV2 1830}

	 panSATDSatdPortalConnectFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GlobalProtect satellite connection to portal failed."
	 ::={panCommonEventEventsV2 1831}

	 panSATDSatdGenericEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1832}

	 panSSLMGRSslmgrConfigP1SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon configuration load phase-1 succeeded."
	 ::={panCommonEventEventsV2 1900}

	 panSSLMGRSslmgrConfigP1FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon configuration load phase-1 failed."
	 ::={panCommonEventEventsV2 1901}

	 panSSLMGRSslmgrConfigP1AbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon configuration load phase-1 aborted."
	 ::={panCommonEventEventsV2 1902}

	 panSSLMGRSslmgrConfigP2SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon configuration load phase-2 succeeded."
	 ::={panCommonEventEventsV2 1903}

	 panSSLMGRSslmgrConfigP2FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon configuration load phase-2 failed."
	 ::={panCommonEventEventsV2 1904}

	 panSSLMGRSslmgrDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon is ready."
	 ::={panCommonEventEventsV2 1905}

	 panSSLMGRSslmgrDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon has exited."
	 ::={panCommonEventEventsV2 1906}

	 panSSLMGRSslmgrCertGenSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR generate certificate succeeded."
	 ::={panCommonEventEventsV2 1907}

	 panSSLMGRSslmgrCertGenFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR generate certificate failed."
	 ::={panCommonEventEventsV2 1908}

	 panSSLMGRSslmgrCertStatusDeletedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR certificate status deleted."
	 ::={panCommonEventEventsV2 1909}

	 panSSLMGRSslmgrCertStatusRevokedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR certificate status revoked."
	 ::={panCommonEventEventsV2 1910}

	 panSSLMGRSslmgrSatelliteInfoInsertedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR satellite info inserted"
	 ::={panCommonEventEventsV2 1911}

	 panSSLMGRSslmgrSatelliteInfoUpdatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR satellite info updated"
	 ::={panCommonEventEventsV2 1912}

	 panSSLMGRSslmgrSatelliteInfoDeletedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR satellite info deleted"
	 ::={panCommonEventEventsV2 1913}

	 panSSLMGRSslmgrCertOcspVerifyFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR certificate ocsp verification failed."
	 ::={panCommonEventEventsV2 1914}

	 panSSLMGRSslmgrCertCrlVerifyFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR certificate crl verification failed."
	 ::={panCommonEventEventsV2 1915}

	 panSSLMGRSslmgrHaFullSyncTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon sync to HA peer."
	 ::={panCommonEventEventsV2 1916}

	 panSSLMGRSslmgrHaNotFullSyncTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR daemon not sync to HA peer."
	 ::={panCommonEventEventsV2 1917}

	 panSSLMGRSslmgrGenericEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 1918}

	 panSSLMGRSslmgrScepCertSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR generate SCEP certificate succeeded."
	 ::={panCommonEventEventsV2 1919}

	 panSSLMGRSslmgrScepCertFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR generate SCEP certificate failed."
	 ::={panCommonEventEventsV2 1920}

	 panSSLMGRSslmgrScepCaCertSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR import SCEP CA certificate succeeded."
	 ::={panCommonEventEventsV2 1921}

	 panSSLMGRSslmgrScepCaCertFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSLMGR import SCEP CA certificate failed."
	 ::={panCommonEventEventsV2 1922}

	 panSSLMGRCaSessionEstablishmentSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CA session establishment succeeded."
	 ::={panCommonEventEventsV2 1923}

	 panSSLMGRCaSessionEstablishmentFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CA session establishment failed."
	 ::={panCommonEventEventsV2 1924}

	 panURLNoUrlDatabaseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "No URL database!"
	 ::={panCommonEventEventsV2 2000}

	 panURLInvalidLicenseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "No URL filtering license or license expired!"
	 ::={panCommonEventEventsV2 2001}

	 panURLFailedToLockUpdateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to lock database update process"
	 ::={panCommonEventEventsV2 2002}

	 panURLConnectionSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connected to update server."
	 ::={panCommonEventEventsV2 2003}

	 panURLConnectionFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to connect to update server."
	 ::={panCommonEventEventsV2 2004}

	 panURLServerIsDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Update Server is down."
	 ::={panCommonEventEventsV2 2005}

	 panURLProxyConnectionFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to connect to proxy server."
	 ::={panCommonEventEventsV2 2006}

	 panURLReceiveDataFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to receive data from update server."
	 ::={panCommonEventEventsV2 2007}

	 panURLDynamicUrlConnectionDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Dynamic URL connection is unavailable."
	 ::={panCommonEventEventsV2 2008}

	 panURLDownloadingUrlDatabaseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Downloading URL database."
	 ::={panCommonEventEventsV2 2009}

	 panURLDownloadUrlDatabaseSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Database was downloaded successfully."
	 ::={panCommonEventEventsV2 2010}

	 panURLUpgradeUrlDatabaseSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Database was upgraded successfully."
	 ::={panCommonEventEventsV2 2011}

	 panURLRevertUrlDatabaseSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Database was reverted successfully."
	 ::={panCommonEventEventsV2 2012}

	 panURLUrlDatabaseIsLatestTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Database is latest."
	 ::={panCommonEventEventsV2 2013}

	 panURLUrlDownloadFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to download a file from the cloud."
	 ::={panCommonEventEventsV2 2014}

	 panURLUrlCloudConnectionFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to connect the cloud."
	 ::={panCommonEventEventsV2 2015}

	 panURLUrlCloudConnectionSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   " Connects to the cloud successfully."
	 ::={panCommonEventEventsV2 2016}

	 panURLUrlBackupSeedSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Backups the URL seed successfully."
	 ::={panCommonEventEventsV2 2017}

	 panURLUrlBackupSeedFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to backup the URL seed."
	 ::={panCommonEventEventsV2 2018}

	 panURLCloudElectionTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "In cloud election process."
	 ::={panCommonEventEventsV2 2019}

	 panURLCloudProcessStartsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cloud process starts."
	 ::={panCommonEventEventsV2 2020}

	 panURLCloudProcessStoppedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Stopped the cloud process."
	 ::={panCommonEventEventsV2 2021}

	 panURLUpdateVersionFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to update to the new seed version."
	 ::={panCommonEventEventsV2 2022}

	 panURLErrorMsgFromCloudTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Got an error message from the cloud."
	 ::={panCommonEventEventsV2 2023}

	 panURLTestASiteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Test-A-Site result."
	 ::={panCommonEventEventsV2 2024}

	 panURLUrlEngineStoppedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Stopped URL engine."
	 ::={panCommonEventEventsV2 2025}

	 panURLUrlEngineStartsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "URL engine starts."
	 ::={panCommonEventEventsV2 2026}

	 panURLStartupFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "URL engine failed to start."
	 ::={panCommonEventEventsV2 2027}

	 panURLHaSyncFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to process HA sync."
	 ::={panCommonEventEventsV2 2028}

	 panURLHaSyncSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA sync processed successfully."
	 ::={panCommonEventEventsV2 2029}

	 panURLSaveMpCacheToDiscFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to save MP cache to disc."
	 ::={panCommonEventEventsV2 2030}

	 panURLSaveMpCacheToDiscSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Saved MP cache to disc successfully."
	 ::={panCommonEventEventsV2 2031}

	 panURLRfsProcessStartsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RFS process starts."
	 ::={panCommonEventEventsV2 2032}

	 panURLRfsProcessStoppedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RFS process was stopped."
	 ::={panCommonEventEventsV2 2033}

	 panURLRfsProcessFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RFS process failed."
	 ::={panCommonEventEventsV2 2034}

	 panURLRequestToCloudFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Request to cloud failed."
	 ::={panCommonEventEventsV2 2035}

	 panURLStartsFromEmptySeedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Starts from empty seed."
	 ::={panCommonEventEventsV2 2036}

	 panURLLoadSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Load the URL seed successfully to MP TRIE."
	 ::={panCommonEventEventsV2 2037}

	 panURLFailedToLockDownloadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to lock download file since is used by another process"
	 ::={panCommonEventEventsV2 2038}

	 panURLEngineStartupFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to start the URL engine."
	 ::={panCommonEventEventsV2 2039}

	 panURLSeedOutOfSyncTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Seed is out of sync."
	 ::={panCommonEventEventsV2 2040}

	 panURLStartsFromBackupSeedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Starts from backed up seed."
	 ::={panCommonEventEventsV2 2041}

	 panURLStartsFromDownloadSeedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Starts from download seed."
	 ::={panCommonEventEventsV2 2042}

	 panURLBackupSeedErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Backup seed error."
	 ::={panCommonEventEventsV2 2043}

	 panURLDownloadSeedErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Download seed error."
	 ::={panCommonEventEventsV2 2044}

	 panUSERIDConnectAgentTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connect to agent"
	 ::={panCommonEventEventsV2 2300}

	 panUSERIDDisconnectAgentTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "disconnect from agent"
	 ::={panCommonEventEventsV2 2301}

	 panUSERIDAgentEventTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "events from agent"
	 ::={panCommonEventEventsV2 2302}

	 panUSERIDConnectAgentFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to agent"
	 ::={panCommonEventEventsV2 2303}

	 panUSERIDAgentVersionMismatchTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "device version is not supported on agent"
	 ::={panCommonEventEventsV2 2304}

	 panUSERIDAgentStatusFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to get status from agent"
	 ::={panCommonEventEventsV2 2305}

	 panUSERIDAgentReadLogErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent failed to read logs"
	 ::={panCommonEventEventsV2 2306}

	 panUSERIDAgentGetDomainErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent failed to get domains"
	 ::={panCommonEventEventsV2 2307}

	 panUSERIDAgentGetUsersErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent failed to get users"
	 ::={panCommonEventEventsV2 2308}

	 panUSERIDAgentGetGroupsErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent failed to get groups"
	 ::={panCommonEventEventsV2 2309}

	 panUSERIDAgentGetConfigErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent failed to get config"
	 ::={panCommonEventEventsV2 2310}

	 panUSERIDAgentNoDomainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent has no domains"
	 ::={panCommonEventEventsV2 2311}

	 panUSERIDAgentNoAllowlistTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Agent has no allow list"
	 ::={panCommonEventEventsV2 2312}

	 panUSERIDConnectLdapSeverTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connect to ldap server"
	 ::={panCommonEventEventsV2 2313}

	 panUSERIDConnectLdapSeverFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to ldap server"
	 ::={panCommonEventEventsV2 2314}

	 panUSERIDGetLdapDataFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to get data from ldap server"
	 ::={panCommonEventEventsV2 2315}

	 panUSERIDHAQueueFullTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA queue is full"
	 ::={panCommonEventEventsV2 2316}

	 panUSERIDConnectClientTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "client is connected"
	 ::={panCommonEventEventsV2 2317}

	 panUSERIDDisconnectClientTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "client is disconnected"
	 ::={panCommonEventEventsV2 2318}

	 panUSERIDConnectServerMonitorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connect to server monitor"
	 ::={panCommonEventEventsV2 2319}

	 panUSERIDConnectServerMonitorFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to server monitor"
	 ::={panCommonEventEventsV2 2320}

	 panUSERIDConnectVmInfoSourceTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "vm-info-source is connected"
	 ::={panCommonEventEventsV2 2321}

	 panUSERIDDisconnectVmInfoSourceTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "vm-info-source is disconnected"
	 ::={panCommonEventEventsV2 2322}

	 panUSERIDConnectVmInfoSourceFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to vm-info-source"
	 ::={panCommonEventEventsV2 2323}

	 panUSERIDRegisteredIpUpdateFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to integrate the update of registered ip addresses"
	 ::={panCommonEventEventsV2 2324}

	 panUSERIDConnectSyslogTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connect to syslog server"
	 ::={panCommonEventEventsV2 2325}

	 panUSERIDDisconnectSyslogTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "disconnect from syslog server"
	 ::={panCommonEventEventsV2 2326}

	 panUSERIDUserGroupCountTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "user group count exceeds threshold"
	 ::={panCommonEventEventsV2 2327}

	 panUSERIDUserCountTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "number of users exceeds threshold"
	 ::={panCommonEventEventsV2 2328}

	 panUSERIDGlobalprotectgatewayInvalidLicenseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "globalprotect gateway license is invalid"
	 ::={panCommonEventEventsV2 2329}

	 panUSERIDCuidStatusTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cloud UserID enable/disable status changed"
	 ::={panCommonEventEventsV2 2330}

	 panUSERIDCuidConfigTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cloud UserID data type role changed"
	 ::={panCommonEventEventsV2 2331}

	 panUSERIDCuidConnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cloud UserID connect/disconnect"
	 ::={panCommonEventEventsV2 2332}

	 panUSERIDDscDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Directory Sync Client daemon is ready"
	 ::={panCommonEventEventsV2 2333}

	 panUSERIDDscHaStatusTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Directory Sync Client HA status changed"
	 ::={panCommonEventEventsV2 2334}

	 panUSERIDDscDatabaseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Directory Sync client database connection success"
	 ::={panCommonEventEventsV2 2335}

	 panUSERIDDssConnSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Directory Sync Service connection Success"
	 ::={panCommonEventEventsV2 2336}

	 panUSERIDDssConnFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Directory Sync Service connection Failed"
	 ::={panCommonEventEventsV2 2337}

	 panUSERIDDssCfgDataTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Directory Sync Service config data Failed"
	 ::={panCommonEventEventsV2 2338}

	 panUSERIDGeneralTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "General"
	 ::={panCommonEventEventsV2 2339}

	 panUSERIDHaIdmgrMergeHasConflictTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA Idmgr mrege has conflict"
	 ::={panCommonEventEventsV2 2340}

	 panUSERIDHaReloadGroupsDiskDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Reload groups files from disk is done"
	 ::={panCommonEventEventsV2 2341}

	 panNATFallbackReportTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Fallback Report"
	 ::={panCommonEventEventsV2 2400}

	 panNATFqdnAddTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Add FQDN IP entry"
	 ::={panCommonEventEventsV2 2401}

	 panNATFqdnDelTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Delete FQDN IP entry"
	 ::={panCommonEventEventsV2 2402}

	 panNATPersistentDippTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Persistent DIPP"
	 ::={panCommonEventEventsV2 2403}

	 panSYSLOGNGSyslogConnStatusTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connection status with syslog server"
	 ::={panCommonEventEventsV2 2500}

	 panLACPLostConnectivityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Peer lost connectivity"
	 ::={panCommonEventEventsV2 2600}

	 panLACPUnresponsiveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Peer not responding"
	 ::={panCommonEventEventsV2 2601}

	 panLACPNegoFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Negotiation failed"
	 ::={panCommonEventEventsV2 2602}

	 panLACPSpeedDuplexTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Speed duplex mismatch"
	 ::={panCommonEventEventsV2 2603}

	 panLACPLinkDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "link down"
	 ::={panCommonEventEventsV2 2604}

	 panLACPLacpDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Port left lacp lag"
	 ::={panCommonEventEventsV2 2605}

	 panLACPLacpUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Port joined lacp lag"
	 ::={panCommonEventEventsV2 2606}

	 panFIPSFipsSelftestUnknownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Unknown FIPS Test failure"
	 ::={panCommonEventEventsV2 2700}

	 panFIPSFipsSelftestTimeoutTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "FIPS test timeout"
	 ::={panCommonEventEventsV2 2701}

	 panFIPSFipsSelftestIntegTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Software Integrety Test"
	 ::={panCommonEventEventsV2 2702}

	 panFIPSFipsSelftestCoreTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Dataplane processor core validation result"
	 ::={panCommonEventEventsV2 2703}

	 panFIPSFipsSelftestAesTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "AES, AES-GCM, AES-CCM, AES-XTS Known Answer Test result"
	 ::={panCommonEventEventsV2 2704}

	 panFIPSFipsSelftestDesTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "3DES Known Answer Test result"
	 ::={panCommonEventEventsV2 2705}

	 panFIPSFipsSelftestDsaTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DSA Known Answer Test result"
	 ::={panCommonEventEventsV2 2706}

	 panFIPSFipsSelftestRsaTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RSA Known Answer Test result"
	 ::={panCommonEventEventsV2 2707}

	 panFIPSFipsSelftestHmacTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HMAC-SHA-1 HMAC-SHA-256 HMAC-SHA-384 HMAC-SHA-512 Known Answer Test result"
	 ::={panCommonEventEventsV2 2708}

	 panFIPSFipsSelftestShaTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SHA-256 SHA-384 SHA-512 Known Answer Test result"
	 ::={panCommonEventEventsV2 2709}

	 panFIPSFipsSelftestDrngTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DRNG Known Answer Test result"
	 ::={panCommonEventEventsV2 2710}

	 panFIPSFipsSelftestNdrngTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "NDRNG Validation Test result"
	 ::={panCommonEventEventsV2 2711}

	 panFIPSFipsSelftestDhParameterTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DH Parameter Test result"
	 ::={panCommonEventEventsV2 2712}

	 panFIPSFipsSelftestDhTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DH Parameter Known Answer Test result"
	 ::={panCommonEventEventsV2 2713}

	 panFIPSFipsFirmwareIntegrityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Firmware Integrity Test result"
	 ::={panCommonEventEventsV2 2714}

	 panFIPSFipsContinuousRngTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Continuous Random Number Generator RNG Test result"
	 ::={panCommonEventEventsV2 2715}

	 panFIPSFipsRsaPairwiseConsistencyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "RSA Pairwise Consistency Test result"
	 ::={panCommonEventEventsV2 2716}

	 panFIPSFipsSelftestSoftwareLoadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Software/Firmware Load Test result"
	 ::={panCommonEventEventsV2 2717}

	 panFIPSFipsSelftestTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "FIPS-CC Mode self-tests"
	 ::={panCommonEventEventsV2 2718}

	 panFIPSFipsSelftestHsmTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HSM self-tests result"
	 ::={panCommonEventEventsV2 2719}

	 panFIPSFipsZeroizationTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Zeroization error"
	 ::={panCommonEventEventsV2 2720}

	 panFIPSFipsKeyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Key failure in openssl"
	 ::={panCommonEventEventsV2 2721}

	 panFIPSFipsCipherTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cipher failure in openssl"
	 ::={panCommonEventEventsV2 2722}

	 panFIPSFipsReplayTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Session replay detected in openssl"
	 ::={panCommonEventEventsV2 2723}

	 panFIPSFipsSslHandshakeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSL session handshake failure detected in openssl"
	 ::={panCommonEventEventsV2 2724}

	 panFIPSFipsContinuousNdrngTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Continuous Random Number Generator Seeding Test result"
	 ::={panCommonEventEventsV2 2725}

	 panFIPSFipsSelftestCmacTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CMAC Known Answer Test result"
	 ::={panCommonEventEventsV2 2726}

	 panFIPSFipsSelftestDrbgTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DRBG Known Answer Test result"
	 ::={panCommonEventEventsV2 2727}

	 panFIPSFipsSelftestEcdsaTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ECDSA Known Answer Test result"
	 ::={panCommonEventEventsV2 2728}

	 panFIPSFipsSelftestEcdhTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ECDH Known Answer Test result"
	 ::={panCommonEventEventsV2 2729}

	 panMDMExceedLicenseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "number of devices exceeds license"
	 ::={panCommonEventEventsV2 2800}

	 panMDMConnectToApnsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connect to APNS"
	 ::={panCommonEventEventsV2 2801}

	 panMDMConnectToApnsFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to APNS"
	 ::={panCommonEventEventsV2 2802}

	 panMDMConnectToGcmTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connect to GCM"
	 ::={panCommonEventEventsV2 2803}

	 panMDMConnectToGcmFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to GCM"
	 ::={panCommonEventEventsV2 2804}

	 panMDMGatewayConnectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "gateway connected"
	 ::={panCommonEventEventsV2 2805}

	 panMDMGatewayDisconnectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "gateway disconnected"
	 ::={panCommonEventEventsV2 2806}

	 panMDMInstallAppContentTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "install app content"
	 ::={panCommonEventEventsV2 2807}

	 panMDMInstallAppContentFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to install app content"
	 ::={panCommonEventEventsV2 2808}

	 panMDMGetScepOtpFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to get OTP from SCEP server"
	 ::={panCommonEventEventsV2 2809}

	 panMDMSendMsgToCloudFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to send message to cloud"
	 ::={panCommonEventEventsV2 2810}

	 panMDMConnectToItunesFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to iTunes"
	 ::={panCommonEventEventsV2 2811}

	 panMDMConnectToAppleVppFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to connect to Apple VPP"
	 ::={panCommonEventEventsV2 2812}

	 panRAIDDiskNotDetectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk not detected"
	 ::={panCommonEventEventsV2 2900}

	 panRAIDPairDetectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "New Disk Pair detected"
	 ::={panCommonEventEventsV2 2901}

	 panRAIDRebuildingTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild started"
	 ::={panCommonEventEventsV2 2902}

	 panRAIDRebuild20Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild 20% done"
	 ::={panCommonEventEventsV2 2903}

	 panRAIDRebuild40Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild 40% done"
	 ::={panCommonEventEventsV2 2904}

	 panRAIDRebuild60Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild 60% done"
	 ::={panCommonEventEventsV2 2905}

	 panRAIDRebuild80Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild 80% done"
	 ::={panCommonEventEventsV2 2906}

	 panRAIDRebuildDoneTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild complete"
	 ::={panCommonEventEventsV2 2907}

	 panRAIDDiskActiveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk is now active"
	 ::={panCommonEventEventsV2 2908}

	 panRAIDDiskFaultyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk marked faulty"
	 ::={panCommonEventEventsV2 2909}

	 panRAIDDiskFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk marked failed"
	 ::={panCommonEventEventsV2 2910}

	 panRAIDSpareMissingTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Spare disk missing"
	 ::={panCommonEventEventsV2 2911}

	 panRAIDSpareMovedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Spare disk moved"
	 ::={panCommonEventEventsV2 2912}

	 panRAIDPairDegradedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Degraded"
	 ::={panCommonEventEventsV2 2913}

	 panRAIDPairDisappearedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair disappeared"
	 ::={panCommonEventEventsV2 2914}

	 panRAIDDiskRemovedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk removed abnormally"
	 ::={panCommonEventEventsV2 2915}

	 panRAIDFsckStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "file system check started"
	 ::={panCommonEventEventsV2 2916}

	 panRAIDFsckEndTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "file system check ended"
	 ::={panCommonEventEventsV2 2917}

	 panRAIDFsckFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "file system check failed"
	 ::={panCommonEventEventsV2 2918}

	 panRAIDMountFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk mount failed"
	 ::={panCommonEventEventsV2 2919}

	 panRAIDRebuildFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disk Pair Rebuild failed"
	 ::={panCommonEventEventsV2 2920}

	 panVMDvfInitSucceedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "VMware dvfilter init succeeded"
	 ::={panCommonEventEventsV2 3000}

	 panVMDvfInitFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "VMware dvfilter init failed"
	 ::={panCommonEventEventsV2 3001}

	 panSSHSshSessionEstablishedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSH session is established"
	 ::={panCommonEventEventsV2 3100}

	 panSSHSshSessionTerminatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSH session is terminated normally"
	 ::={panCommonEventEventsV2 3101}

	 panSSHSshSessionEstablishmentFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSH session establishment failed"
	 ::={panCommonEventEventsV2 3102}

	 panSSHSshSessionDisconnectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSH session is disconnected by server"
	 ::={panCommonEventEventsV2 3103}

	 panSSHSshConnectionTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SSH conection is accepted but not authenticated yet"
	 ::={panCommonEventEventsV2 3104}

	 panTLSTlsSessionEstablishedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS session is established"
	 ::={panCommonEventEventsV2 3200}

	 panTLSTlsSessionTerminatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS session is terminated normally"
	 ::={panCommonEventEventsV2 3201}

	 panTLSTlsSessionEstablishmentFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS session establishment failed"
	 ::={panCommonEventEventsV2 3202}

	 panTLSTlsSessionDisconnectedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS session is disconnected by server"
	 ::={panCommonEventEventsV2 3203}

	 panTLSTlsEdlAuthFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS server certificate authentication failed for EDL"
	 ::={panCommonEventEventsV2 3204}

	 panTLSTlsX509ServerIdentFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 Server Identifier failed"
	 ::={panCommonEventEventsV2 3205}

	 panTLSTlsX509ValidationFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 Validation failed"
	 ::={panCommonEventEventsV2 3206}

	 panTLSTlsX509EkuServerAuthFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 XKU Server auth failed"
	 ::={panCommonEventEventsV2 3207}

	 panTLSTlsX509ClientIdentFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 Client Identifier failed"
	 ::={panCommonEventEventsV2 3208}

	 panTLSTlsX509EkuClientAuthFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 XKU Client auth failed"
	 ::={panCommonEventEventsV2 3209}

	 panTLSTlsX509EkuClientAuthSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 XKU Client auth success."
	 ::={panCommonEventEventsV2 3210}

	 panTLSPanoramaAuthFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Panorama auth failed"
	 ::={panCommonEventEventsV2 3211}

	 panTLSPanoramaAuthSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Panorama auth succeeded"
	 ::={panCommonEventEventsV2 3212}

	 panTLSPanosAuthFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PanOS auth failed"
	 ::={panCommonEventEventsV2 3213}

	 panTLSPanosAuthSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "PanOS auth success"
	 ::={panCommonEventEventsV2 3214}

	 panTLSTlsX509EkuCodeSigningExtCheckFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 XKU Client auth failed"
	 ::={panCommonEventEventsV2 3215}

	 panTLSTlsX509OcspCrlCheckFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 CRL/OCSP check failed"
	 ::={panCommonEventEventsV2 3216}

	 panTLSTlsX509UntrustedCertIssuerFoundTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "TLS X509 Untrusted issuer found"
	 ::={panCommonEventEventsV2 3217}

	 panTLSMfaAuthFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "MFA server validation failed"
	 ::={panCommonEventEventsV2 3218}

	 panTLSCertificateRenewalTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Certificate renewal triggered"
	 ::={panCommonEventEventsV2 3219}

	 panTLSCertificateExpiredTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Certificate expired"
	 ::={panCommonEventEventsV2 3220}

	 panLLDPRxErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "receive error"
	 ::={panCommonEventEventsV2 3300}

	 panLLDPMibChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "mib update event"
	 ::={panCommonEventEventsV2 3301}

	 panLLDPTooManyNeighborsTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "too many neighbors"
	 ::={panCommonEventEventsV2 3302}

	 panLLDPTooManyNeighborsTimerClearedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "clear tooManyNeighbors timer"
	 ::={panCommonEventEventsV2 3303}

	 panLLDPOtherTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "other reasons"
	 ::={panCommonEventEventsV2 3304}

	 panLLDPTxErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "transmit error"
	 ::={panCommonEventEventsV2 3305}

	 panFBWildfireWrongCloudTypeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire disabled due to wrong cloud type"
	 ::={panCommonEventEventsV2 3400}

	 panFBWildfireDisabledByCloudTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire Cloud does not support current PANOS version"
	 ::={panCommonEventEventsV2 3401}

	 panFBWildfireNoPolicyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire disabled due to configuration"
	 ::={panCommonEventEventsV2 3402}

	 panFBWildfireNoLicenseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire registration failed due to invalid license"
	 ::={panCommonEventEventsV2 3403}

	 panFBWildfireInvalidCloudInfoTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WildFire registration failed due to invalid cloud info"
	 ::={panCommonEventEventsV2 3404}

	 panBFDExpiredTimeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Control detection time expired"
	 ::={panCommonEventEventsV2 3500}

	 panBFDNeighborDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Neighbor signaled session down"
	 ::={panCommonEventEventsV2 3501}

	 panBFDForwardPlaneResetTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Forwarding plane reset"
	 ::={panCommonEventEventsV2 3502}

	 panBFDAdminDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Administrative down"
	 ::={panCommonEventEventsV2 3503}

	 panBFDSessionStateChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Session state change"
	 ::={panCommonEventEventsV2 3504}

	 panBFDSessionCapacityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "BFD session capacity reached"
	 ::={panCommonEventEventsV2 3505}

	 panAUTHGeneralTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "General auth event"
	 ::={panCommonEventEventsV2 3600}

	 panAUTHAuthServerDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not contact auth server"
	 ::={panCommonEventEventsV2 3601}

	 panAUTHCreateAdminAcctErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not create admin account"
	 ::={panCommonEventEventsV2 3602}

	 panAUTHAuthFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Authentication attempt faliure"
	 ::={panCommonEventEventsV2 3603}

	 panAUTHAuthSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Authentication attempt success"
	 ::={panCommonEventEventsV2 3604}

	 panAUTHSamlClientRedirectTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML client redirect"
	 ::={panCommonEventEventsV2 3605}

	 panAUTHSamlIdpActivityTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML IdP activity"
	 ::={panCommonEventEventsV2 3606}

	 panAUTHSamlCertificateWarningTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML IdP certificate expiring"
	 ::={panCommonEventEventsV2 3607}

	 panAUTHSamlCertificateErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML IdP or SP certificate error"
	 ::={panCommonEventEventsV2 3608}

	 panAUTHSamlMessageParseErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML message parse error"
	 ::={panCommonEventEventsV2 3609}

	 panAUTHSamlOutOfBandMessageTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML SP received unsolicited message"
	 ::={panCommonEventEventsV2 3610}

	 panAUTHSamlSignatureValidatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML signature in message is validated"
	 ::={panCommonEventEventsV2 3611}

	 panAUTHEdlCliAuthFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "EDL client authentication failed"
	 ::={panCommonEventEventsV2 3612}

	 panAUTHLogoutSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Logout is successful"
	 ::={panCommonEventEventsV2 3613}

	 panAUTHLogoutFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Logout is failed"
	 ::={panCommonEventEventsV2 3614}

	 panAUTHIdpInitiatedLogOutSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML IdP initiated Logout is successful"
	 ::={panCommonEventEventsV2 3615}

	 panAUTHSpInitiatedLogOutSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SAML SP initiated Logout is successful"
	 ::={panCommonEventEventsV2 3616}

	 panAUTHUserPasswordChangeSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "User password change is successful"
	 ::={panCommonEventEventsV2 3617}

	 panAUTHUserPasswordChangeFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "User password change is failed"
	 ::={panCommonEventEventsV2 3618}

	 panAUTHCasClientRedirectTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS client redirect"
	 ::={panCommonEventEventsV2 3619}

	 panAUTHCasTokenReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS token is received"
	 ::={panCommonEventEventsV2 3620}

	 panAUTHCasTokenValidatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS token is validated"
	 ::={panCommonEventEventsV2 3621}

	 panAUTHCasTokenInvalidatedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS token is invalidated"
	 ::={panCommonEventEventsV2 3622}

	 panAUTHCasTokenParseErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS token has parse error"
	 ::={panCommonEventEventsV2 3623}

	 panAUTHCasMfaInfoTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS multi factor authentication info"
	 ::={panCommonEventEventsV2 3624}

	 panAUTHCasCertificateWarningTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS or device certificate expiring"
	 ::={panCommonEventEventsV2 3625}

	 panAUTHCasCertificateErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CAS or device certificate error"
	 ::={panCommonEventEventsV2 3626}

	 panAUTHCasMessageTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Message from CAS"
	 ::={panCommonEventEventsV2 3627}

	 panAUTHAuthServerUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Contact auth server successfully"
	 ::={panCommonEventEventsV2 3628}

	 panAUTHHTTP407Trap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "407 Proxy Authentication Required"
	 ::={panCommonEventEventsV2 3629}

	 panAUTHTacacsAcctTxFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Failed to send TACACS+ acct record to any of the servers in accounting-server-profile"
	 ::={panCommonEventEventsV2 3630}

	 panAUTHTacacsAcctTxSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Successfully sent TACACS+ acct record to a server in accounting-server-profile"
	 ::={panCommonEventEventsV2 3631}

	 panAUTHExitAuthSequenceTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Exit authentication sequence"
	 ::={panCommonEventEventsV2 3632}

	 panAUTHCantGetKcdKrbtgtTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not get ticket granting ticket for on-prem KCD agent"
	 ::={panCommonEventEventsV2 3633}

	 panAUTHGetKcdKrbtgtTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Get ticket granting ticket for on-prem KCD agent"
	 ::={panCommonEventEventsV2 3634}

	 panAUTHCantMapUidToUsernameTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not map user id to username"
	 ::={panCommonEventEventsV2 3635}

	 panAUTHCantMapRidToDelegationTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not map auth policy rule id to delegation profile"
	 ::={panCommonEventEventsV2 3636}

	 panAUTHCantS4u2selfTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can not get a service ticket to itself on behalf of a user"
	 ::={panCommonEventEventsV2 3637}

	 panAUTHS4u2selfTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Get a service ticket to itself on behalf of a user"
	 ::={panCommonEventEventsV2 3638}

	 panAUTHCantS4u2proxyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can nott get a service ticket to another service on behalf of a user"
	 ::={panCommonEventEventsV2 3639}

	 panAUTHS4u2proxyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Get a service ticket to another service on behalf of a user"
	 ::={panCommonEventEventsV2 3640}

	 panAUTHCantCreateApReqTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Can nott create AP_REQ payload (SPNEGO token)"
	 ::={panCommonEventEventsV2 3641}

	 panAUTHCreateApReqTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Create AP_REQ payload (SPNEGO token)"
	 ::={panCommonEventEventsV2 3642}

	 panAUTHCreateApReqTimedoutTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Create AP_REQ payload (SPNEGO token) : timed out"
	 ::={panCommonEventEventsV2 3643}

	 panCLUSTERDClusterDaemonInitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon is initializing."
	 ::={panCommonEventEventsV2 3700}

	 panCLUSTERDClusterDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon is ready."
	 ::={panCommonEventEventsV2 3701}

	 panCLUSTERDClusterDaemonExitTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon has exited."
	 ::={panCommonEventEventsV2 3702}

	 panCLUSTERDClusterDaemonCfgTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon is unable to get last cfg from cfgagent. Out of retries."
	 ::={panCommonEventEventsV2 3703}

	 panCLUSTERDClusterDaemonCfgGiveupTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon is unable to get last cfg from cfgagent. Retrying."
	 ::={panCommonEventEventsV2 3704}

	 panCLUSTERDClusterSplitBrainEnterTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster enters split-brain mode."
	 ::={panCommonEventEventsV2 3705}

	 panCLUSTERDClusterSplitBrainLeaveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster left split-brain mode."
	 ::={panCommonEventEventsV2 3706}

	 panCLUSTERDClusterCfgModeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster node mode is changed. "
	 ::={panCommonEventEventsV2 3707}

	 panCLUSTERDClusterCfgClusterNameTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster name is changed. "
	 ::={panCommonEventEventsV2 3708}

	 panCLUSTERDClusterCfgNodeNameTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster node name is changed. "
	 ::={panCommonEventEventsV2 3709}

	 panCLUSTERDClusterCfgNodeAddrTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster node address is changed. "
	 ::={panCommonEventEventsV2 3710}

	 panCLUSTERDClusterEngineSuspendOnTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine entered suspend mode."
	 ::={panCommonEventEventsV2 3711}

	 panCLUSTERDClusterEngineSuspendOffTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine left suspend mode."
	 ::={panCommonEventEventsV2 3712}

	 panCLUSTERDClusterEngineStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine will be started for: "
	 ::={panCommonEventEventsV2 3713}

	 panCLUSTERDClusterServiceReadyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster service is ready."
	 ::={panCommonEventEventsV2 3714}

	 panCLUSTERDClusterServiceUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster service up: "
	 ::={panCommonEventEventsV2 3715}

	 panCLUSTERDClusterServiceDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster service down: "
	 ::={panCommonEventEventsV2 3716}

	 panCLUSTERDClusterJobRequestTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 3717}

	 panCLUSTERDClusterJobResponseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 3718}

	 panCLUSTERDClusterJobFinishTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 3719}

	 panCLUSTERDClusterJobCancelTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   ""
	 ::={panCommonEventEventsV2 3720}

	 panCLUSTERDClusterHaSyncPeerBackupTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon HA sync started when peer device becomes passive."
	 ::={panCommonEventEventsV2 3721}

	 panCLUSTERDClusterHaSyncSelfMasterTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon HA sync started when local device becomes master."
	 ::={panCommonEventEventsV2 3722}

	 panCLUSTERDClusterConfigP1SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon configuration load phase-1 succeeded."
	 ::={panCommonEventEventsV2 3723}

	 panCLUSTERDClusterConfigP1FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon configuration load phase-1 failed."
	 ::={panCommonEventEventsV2 3724}

	 panCLUSTERDClusterConfigP1AbortTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon configuration load phase-1 aborted."
	 ::={panCommonEventEventsV2 3725}

	 panCLUSTERDClusterConfigP2SuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon configuration load phase-2 succeeded."
	 ::={panCommonEventEventsV2 3726}

	 panCLUSTERDClusterConfigP2FailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster daemon configuration load phase-2 failed."
	 ::={panCommonEventEventsV2 3727}

	 panCLUSTERDClusterEngineControllerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine has started as controller role."
	 ::={panCommonEventEventsV2 3728}

	 panCLUSTERDClusterEngineServerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine has started as worker role - server mode."
	 ::={panCommonEventEventsV2 3729}

	 panCLUSTERDClusterEngineWorkerTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine has started as worker role."
	 ::={panCommonEventEventsV2 3730}

	 panCLUSTERDClusterEngineReloadTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine has reloading new configuration."
	 ::={panCommonEventEventsV2 3731}

	 panCLUSTERDClusterEngineRestartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine will be restarted with new configuration."
	 ::={panCommonEventEventsV2 3732}

	 panCLUSTERDClusterEngineShutdownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine has shutdown."
	 ::={panCommonEventEventsV2 3733}

	 panCLUSTERDClusterSelfJoinTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Local node joined cluster:"
	 ::={panCommonEventEventsV2 3734}

	 panCLUSTERDClusterSelfDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Local node lost connection with cluster:"
	 ::={panCommonEventEventsV2 3735}

	 panCLUSTERDClusterSelfLeaveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Local node left cluster:"
	 ::={panCommonEventEventsV2 3736}

	 panCLUSTERDClusterOtherJoinTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Peer node joined cluster:"
	 ::={panCommonEventEventsV2 3737}

	 panCLUSTERDClusterOtherDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Peer node lost connection with cluster:"
	 ::={panCommonEventEventsV2 3738}

	 panCLUSTERDClusterOtherLeaveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Peer node left cluster:"
	 ::={panCommonEventEventsV2 3739}

	 panCLUSTERDClusterOtherIpIncompatibleTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Peer node IP is not compatible with current cluster interface IP"
	 ::={panCommonEventEventsV2 3740}

	 panIPV6NDIpv6DisabledTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Neighbor IPv6 disabled"
	 ::={panCommonEventEventsV2 3800}

	 panIPV6NDDuplicatedIPv6AddressFoundTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Neighbor DAD"
	 ::={panCommonEventEventsV2 3801}

	 panIPV6NDInconsistentRaMessageReceivedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Neighbor inconsistent RA"
	 ::={panCommonEventEventsV2 3802}

	 panDYNAMICUPDATESPaloAltoNetworksMessageTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Received Palo Alto Networks secure content related message"
	 ::={panCommonEventEventsV2 3900}

	 panUUIDPolicyRuleUuidModifiedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Received Policy Rule UUID change update"
	 ::={panCommonEventEventsV2 4000}

	 panGRETunnelStatusUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GRE tunnel status changed to up"
	 ::={panCommonEventEventsV2 4100}

	 panGRETunnelStatusDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GRE tunnel status changed to down"
	 ::={panCommonEventEventsV2 4101}

	 panGRETunnelRecurRoutingTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GRE tunnel status changed to down, recursive routing"
	 ::={panCommonEventEventsV2 4102}

	 panPANOCHECKPanoramaCheckSkipTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Skipping panorama check"
	 ::={panCommonEventEventsV2 4200}

	 panPANOCHECKPanoramaCheckAutoDisabledTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Disabling feature implcitly for this commit"
	 ::={panCommonEventEventsV2 4201}

	 panPANOCHECKPanoramaCheckAutoRevertTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Revrting configuration"
	 ::={panCommonEventEventsV2 4202}

	 panPANOCHECKPanoramaCheckTestTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Hourly cron job"
	 ::={panCommonEventEventsV2 4203}

	 panSDWANSdwanVifStatusUpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SD-WAN vif status change to up."
	 ::={panCommonEventEventsV2 4300}

	 panSDWANSdwanVifStatusDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "SD-WAN vif status change to down."
	 ::={panCommonEventEventsV2 4301}

	 panDTCollectNowCancellingTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "collect-now cancelling "
	 ::={panCommonEventEventsV2 4400}

	 panDTSendSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "successfully sent"
	 ::={panCommonEventEventsV2 4401}

	 panDTSendFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed sending the files"
	 ::={panCommonEventEventsV2 4402}

	 panDTConfigGenerateSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "successfully generate new config files"
	 ::={panCommonEventEventsV2 4403}

	 panDTConfigLoadFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to load config file"
	 ::={panCommonEventEventsV2 4404}

	 panDTConfigReloadFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to reload config files"
	 ::={panCommonEventEventsV2 4405}

	 panDTConfigReplaceFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failed to replace config files"
	 ::={panCommonEventEventsV2 4406}

	 panCTDAGENTConnectionStatusChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "connection status has changed"
	 ::={panCommonEventEventsV2 4500}

	 panCTDAGENTConfigurationFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failure caused by confiuration"
	 ::={panCommonEventEventsV2 4501}

	 panCTDAGENTLicenseFailureTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "failure caused by license"
	 ::={panCommonEventEventsV2 4502}

	 panCTDAGENTResourceIssueTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "resource related issue has occurred"
	 ::={panCommonEventEventsV2 4503}

	 panSCHEDPUSHSchedSkipTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Skipping push as all devices are in-sync"
	 ::={panCommonEventEventsV2 4600}

	 panSCHEDPUSHSchedExecTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Successfully scheduled push to devices"
	 ::={panCommonEventEventsV2 4601}

	 panAUTOPUSHAutoPushContentAppPushedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "App content is pushed to device"
	 ::={panCommonEventEventsV2 4700}

	 panAUTOPUSHAutoPushContentAppSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "App content is installed on device"
	 ::={panCommonEventEventsV2 4701}

	 panAUTOPUSHAutoPushContentAppFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "App content is failed to be installed on device"
	 ::={panCommonEventEventsV2 4702}

	 panAUTOPUSHAutoPushContentThreatPushedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Threat content is pushed to device"
	 ::={panCommonEventEventsV2 4703}

	 panAUTOPUSHAutoPushContentThreatSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Threat content is installed on device"
	 ::={panCommonEventEventsV2 4704}

	 panAUTOPUSHAutoPushContentThreatFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Threat content is failed to be installed on device"
	 ::={panCommonEventEventsV2 4705}

	 panAUTOPUSHAutoPushContentAntivirusPushedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Antivirus content is pushed to device"
	 ::={panCommonEventEventsV2 4706}

	 panAUTOPUSHAutoPushContentAntivirusSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Antivirus content is installed on device"
	 ::={panCommonEventEventsV2 4707}

	 panAUTOPUSHAutoPushContentAntivirusFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Antivirus content is failed to be installed on device"
	 ::={panCommonEventEventsV2 4708}

	 panMonitoringDeviatingDeviceTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Monitoring deviating devices"
	 ::={panCommonEventEventsV2 4800}

	 panACEGeneralTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "General"
	 ::={panCommonEventEventsV2 4900}

	 panACEConnectionTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "gRPC connection to cloud"
	 ::={panCommonEventEventsV2 4901}

	 panACETaskTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud application task info"
	 ::={panCommonEventEventsV2 4902}

	 panACEVersionTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud application version"
	 ::={panCommonEventEventsV2 4903}

	 panAUDITGuiTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GUI activity"
	 ::={panCommonEventEventsV2 5000}

	 panAUDITCliTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "CLI operational command"
	 ::={panCommonEventEventsV2 5001}

	 panAUDITGuiOpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GUI operational command"
	 ::={panCommonEventEventsV2 5002}

	 panAUDITGnmiTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "GNMI request"
	 ::={panCommonEventEventsV2 5003}

	 panAUDITApiTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "REST API request"
	 ::={panCommonEventEventsV2 5004}

	 panBROKERMonitorFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Monitor failed"
	 ::={panCommonEventEventsV2 5100}

	 panBROKERMonitorRecoverTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Monitor recovered"
	 ::={panCommonEventEventsV2 5101}

	 panBROKERMonitorPathFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Path monitor failed"
	 ::={panCommonEventEventsV2 5102}

	 panBROKERMonitorPathRecoverTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Path monitor recovered"
	 ::={panCommonEventEventsV2 5103}

	 panBROKERMonitorHttpFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HTTP monitor failed"
	 ::={panCommonEventEventsV2 5104}

	 panBROKERMonitorHttpRecoverTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HTTP monitor recovered"
	 ::={panCommonEventEventsV2 5105}

	 panBROKERMonitorLatencyExceedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Latency exceeded"
	 ::={panCommonEventEventsV2 5106}

	 panBROKERMonitorLatencyRestoreTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Latency restored"
	 ::={panCommonEventEventsV2 5107}

	 panBROKERIcmpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "ICMP message received"
	 ::={panCommonEventEventsV2 5108}

	 panDDNSDdnsUpdateTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DDNS update"
	 ::={panCommonEventEventsV2 5200}

	 panDDNSDdnsRefreshTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DDNS refresh"
	 ::={panCommonEventEventsV2 5201}

	 panDDNSDdnsRemoveTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DDNS remove"
	 ::={panCommonEventEventsV2 5202}

	 panDDNSDdnsUnsupportedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DDNS unsupported"
	 ::={panCommonEventEventsV2 5203}

	 panDDNSDdnsDhcpTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "DDNS address released"
	 ::={panCommonEventEventsV2 5204}

	 panDEBUGPacketDiagLogTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Packet-diag logging event"
	 ::={panCommonEventEventsV2 5300}

	 panDNSSECPANELOGEVENTCACHEFAILTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cache initialization from storage failed"
	 ::={panCommonEventEventsV2 5400}

	 panDNSSECPANELOGEVENTCACHESUCCESSTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cache initialization from storage successful"
	 ::={panCommonEventEventsV2 5401}

	 panDNSSECPANELOGEVENTDNSCLOUDCONNECTIONNOHOSTTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service DNS resolution failed"
	 ::={panCommonEventEventsV2 5402}

	 panDNSSECPANELOGEVENTDNSCLOUDCONNECTIONNOROUTETrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service network connectivity failed"
	 ::={panCommonEventEventsV2 5403}

	 panDNSSECPANELOGEVENTDNSCLOUDCONNECTIONREFUSEDTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service connection refused"
	 ::={panCommonEventEventsV2 5404}

	 panDNSSECPANELOGEVENTDNSCLOUDUNAVAILABLETrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service unavailable"
	 ::={panCommonEventEventsV2 5405}

	 panDNSSECPANELOGEVENTDNSCLOUDTIMEOUTTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud query timeout"
	 ::={panCommonEventEventsV2 5406}

	 panDNSSECPANELOGEVENTDNSTELECLOUDCONNECTIONNOHOSTTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "telemetry cloud service DNS resolution failed"
	 ::={panCommonEventEventsV2 5407}

	 panDNSSECPANELOGEVENTDNSTELECLOUDCONNECTIONNOROUTETrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "telemetry cloud service network connectivity failed"
	 ::={panCommonEventEventsV2 5408}

	 panDNSSECPANELOGEVENTDNSTELECLOUDCONNECTIONREFUSEDTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "telemetry cloud service connection refused"
	 ::={panCommonEventEventsV2 5409}

	 panDNSSECPANELOGEVENTDNSTELECLOUDUNAVAILABLETrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "telemetry cloud service unavailable"
	 ::={panCommonEventEventsV2 5410}

	 panDNSSECPANELOGEVENTDNSTELECLOUDTIMEOUTTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "telemetry cloud query timeout"
	 ::={panCommonEventEventsV2 5411}

	 panIOTGeneralTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "General"
	 ::={panCommonEventEventsV2 5500}

	 panIOTHaQueueFullTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "HA queue is full"
	 ::={panCommonEventEventsV2 5501}

	 panIOTIcdHaStatusTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Identity client HA status changed"
	 ::={panCommonEventEventsV2 5502}

	 panIOTLicenseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IoT license status changed"
	 ::={panCommonEventEventsV2 5503}

	 panIOTIcdDaemonStartTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Identity client daemon is ready"
	 ::={panCommonEventEventsV2 5504}

	 panIOTGrpcConnSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "gRPC connection failed"
	 ::={panCommonEventEventsV2 5505}

	 panIOTGrpcConnFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "gRPC connection success"
	 ::={panCommonEventEventsV2 5506}

	 panIOTPolicyRecommendationTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "IoT policy recommendation triggered"
	 ::={panCommonEventEventsV2 5507}

	 panIOTEalFormatChangedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Identity client EAL message format changed"
	 ::={panCommonEventEventsV2 5508}

	 panIOTDatabaseTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Identity client database connection success"
	 ::={panCommonEventEventsV2 5509}

	 panPLUGINGeneralTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Plugin"
	 ::={panCommonEventEventsV2 5600}

	 panRESCTRLMemLimitExceededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Memory limit exceeded"
	 ::={panCommonEventEventsV2 5700}

	 panRESCTRLMemUsageNormalTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Memory usage normal"
	 ::={panCommonEventEventsV2 5701}

	 panRTSIGMalForwardTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "malicious query forwarded"
	 ::={panCommonEventEventsV2 5800}

	 panRTSIGCacheInitFailTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cache initialization from storage failed"
	 ::={panCommonEventEventsV2 5801}

	 panRTSIGCacheInitSuccessTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cache initialization from storage successful"
	 ::={panCommonEventEventsV2 5802}

	 panRTSIGCloudFailNohostTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service DNS resolution failed"
	 ::={panCommonEventEventsV2 5803}

	 panRTSIGCloudFailNorouteTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service network connectivity failed"
	 ::={panCommonEventEventsV2 5804}

	 panRTSIGCloudFailRefusedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service connection refused"
	 ::={panCommonEventEventsV2 5805}

	 panRTSIGCloudFailDownTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud service unavailable"
	 ::={panCommonEventEventsV2 5806}

	 panRTSIGCloudQueryTimeoutTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "cloud query timeout"
	 ::={panCommonEventEventsV2 5807}

	 panWILDFIREAPPLIANCETrustedSignerLookupFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Trusted signer lookup failed"
	 ::={panCommonEventEventsV2 5900}

	 panWILDFIREAPPLIANCENetworkUnavailableTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Network is not accessible from virtual machine"
	 ::={panCommonEventEventsV2 5901}

	 panWILDFIREAPPLIANCEAnonymousNetworkUnavailableTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Tor service is not accessible by vm"
	 ::={panCommonEventEventsV2 5902}

	 panWILDFIREAPPLIANCEAnonymousNetworkUnhealthyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Anonymous service is down"
	 ::={panCommonEventEventsV2 5903}

	 panWILDFIREAPPLIANCESiggenFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Siggen failed for file"
	 ::={panCommonEventEventsV2 5904}

	 panWILDFIREAPPLIANCECloudLookupSuccededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cloud verdict lookup succeed"
	 ::={panCommonEventEventsV2 5905}

	 panWILDFIREAPPLIANCECloudLookupFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cloud verdict lookup failed"
	 ::={panCommonEventEventsV2 5906}

	 panWILDFIREAPPLIANCEClusterModeChangeTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster node mode changed to "
	 ::={panCommonEventEventsV2 5907}

	 panWILDFIREAPPLIANCEClusterEngineRoleTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster engine started as "
	 ::={panCommonEventEventsV2 5908}

	 panWILDFIREAPPLIANCEClusterEnteredSplitBrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster enters split-brain mode."
	 ::={panCommonEventEventsV2 5909}

	 panWILDFIREAPPLIANCEClusterLeftSplitBrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster leaves split-brain mode."
	 ::={panCommonEventEventsV2 5910}

	 panWILDFIREAPPLIANCEClusterDecommissionedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster node decommissioned "
	 ::={panCommonEventEventsV2 5911}

	 panWILDFIREAPPLIANCEClusterFormationGlobalQueueSucceededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global queue (rabbitmq) cluster formation succeeded with status: "
	 ::={panCommonEventEventsV2 5912}

	 panWILDFIREAPPLIANCEClusterFormationGlobalQueueFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global queue (rabbitmq) cluster formation failed with status: "
	 ::={panCommonEventEventsV2 5913}

	 panWILDFIREAPPLIANCEClusterGlobalQueueUnhealthyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global queue (rabbitmq) cluster is unhealthy."
	 ::={panCommonEventEventsV2 5914}

	 panWILDFIREAPPLIANCEClusterGlobalQueueSplitbrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global queue (rabbitmq) cluster is in split-brain mode."
	 ::={panCommonEventEventsV2 5915}

	 panWILDFIREAPPLIANCEClusterFormationGlobalDatabaseSucceededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global database (redis) cluster formation succeeded with status: "
	 ::={panCommonEventEventsV2 5916}

	 panWILDFIREAPPLIANCEClusterFormationGlobalDatabaseFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global database (redis) cluster formation failed with status: "
	 ::={panCommonEventEventsV2 5917}

	 panWILDFIREAPPLIANCEClusterGlobalDatabaseUnhealthyTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global database (redis) cluster is unhealthy."
	 ::={panCommonEventEventsV2 5918}

	 panWILDFIREAPPLIANCEClusterGlobalDatabaseUnavailableTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global database (redis) cluster is unavailable."
	 ::={panCommonEventEventsV2 5919}

	 panWILDFIREAPPLIANCEClusterGlobalDatabaseSplitbrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Global database (redis) cluster is in split-brain mode."
	 ::={panCommonEventEventsV2 5920}

	 panWILDFIREAPPLIANCEClusterSiggenStatusTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Signature generation service "
	 ::={panCommonEventEventsV2 5921}

	 panWILDFIREAPPLIANCEClusterSiggenErrorTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WF private signature package could not be generated"
	 ::={panCommonEventEventsV2 5922}

	 panWILDFIREAPPLIANCESiggenPkgGenFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WF private signature package could not be generated"
	 ::={panCommonEventEventsV2 5923}

	 panWILDFIREAPPLIANCESiggenPkgGenSplitbrainTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "WF private signature package is in split-brain mode"
	 ::={panCommonEventEventsV2 5924}

	 panWILDFIREAPPLIANCEClusterDataMigrationStartedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster data migration started"
	 ::={panCommonEventEventsV2 5925}

	 panWILDFIREAPPLIANCEClusterDataMigrationSucceededTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster data migration succeeded - DataMigrationDone"
	 ::={panCommonEventEventsV2 5926}

	 panWILDFIREAPPLIANCEClusterDataMigrationFailedTrap NOTIFICATION-TYPE
	   OBJECTS {
		 panReceiveTime, panSerial, panEventType, panEventSubType, panVsys, panSeqno, panActionflags, panHostname, panSystemEventId, panSystemObject, panSystemModule, panSystemSeverity, panSystemDescription
		 }
	 STATUS 	 current
	 DESCRIPTION
	   "Cluster data migration failed - DataMigrationFailed"
	 ::={panCommonEventEventsV2 5927}
END
