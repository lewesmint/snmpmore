MY-AGENT-MIB DEFINITIONS ::= BEGIN

IMPORTS
    MODULE-IDENTITY, OBJECT-TYPE, Integer32, Unsigned32, enterprises
        FROM SNMPv2-SMI
    DisplayString
        FROM SNMPv2-TC;

myAgent MODULE-IDENTITY
    LAST-UPDATED    "202601160000Z"
    ORGANIZATION    "Mintz Example"
    CONTACT-INFO    "mintz@example.com"
    DESCRIPTION     "A demo MIB for a custom SNMP agent."
    ::= { enterprises 99999 }

-- Scalars
myString OBJECT-TYPE
    SYNTAX      DisplayString
    MAX-ACCESS  read-only
    STATUS      current
    DESCRIPTION "A hello string."
    ::= { myAgent 1 }

myCounter OBJECT-TYPE
    SYNTAX      Integer32
    MAX-ACCESS  read-only
    STATUS      current
    DESCRIPTION "A counter."
    ::= { myAgent 2 }

myGauge OBJECT-TYPE
    SYNTAX      Integer32
    MAX-ACCESS  read-only
    STATUS      current
    DESCRIPTION "A gauge."
    ::= { myAgent 3 }

-- Table
myTable OBJECT-TYPE
    SYNTAX      SEQUENCE OF MyTableEntry
    MAX-ACCESS  not-accessible
    STATUS      current
    DESCRIPTION "A table of sensors."
    ::= { myAgent 4 }

myTableEntry OBJECT-TYPE
    SYNTAX      MyTableEntry
    MAX-ACCESS  not-accessible
    STATUS      current
    DESCRIPTION "A row in the sensor table."
    INDEX       { myTableIndex }
    ::= { myTable 1 }

MyTableEntry ::= SEQUENCE {
    myTableIndex   Integer32,
    myTableName    DisplayString,
    myTableValue   Integer32,
    myTableStatus  DisplayString
}

myTableIndex OBJECT-TYPE
    SYNTAX      Integer32
    MAX-ACCESS  read-only
    STATUS      current
    DESCRIPTION "Row index."
    ::= { myTableEntry 1 }

myTableName OBJECT-TYPE
    SYNTAX      DisplayString
    MAX-ACCESS  read-only
    STATUS      current
    DESCRIPTION "Sensor name."
    ::= { myTableEntry 2 }

myTableValue OBJECT-TYPE
    SYNTAX      Integer32
    MAX-ACCESS  read-only
    STATUS      current
    DESCRIPTION "Sensor value."
    ::= { myTableEntry 3 }

myTableStatus OBJECT-TYPE
    SYNTAX      DisplayString
    MAX-ACCESS  read-only
    STATUS      current
    DESCRIPTION "Sensor status."
    ::= { myTableEntry 4 }

END
